FME workspace 1_integration_produit_siqo.fmw

Parameters:
- SourceDataset_POSTGRES = srv_sig_1   # Connection
- DestDataset_POSTGRES = srv_sig_1   # Connection

Readers:
- POSTGRES_1: POSTGRES from $(SourceDataset_POSTGRES)

Writers:
- POSTGRES_2: POSTGRES to $(DestDataset_POSTGRES)

Note: requete les denomination dans la base SIQO
SQLCreator
    DATASET = bsi inao
    EXPOSED_ATTRIBUTE_LIST = id_siqo,id_app,appellation,id_denom,denomination,produit,categorie,signe,lst_centre,lst_id_cvi
    FORMAT = MYSQL
    MYSQL_NAMED_CONNECTION = bsi inao
    MYSQL_QUERY_FEATURE_TYPES_FOR_MERGE_FILTERS = Yes
    SQL_STATEMENT:
      SELECT DISTINCT
          concat(lpad(p.ID_APPELLATION,4,'0'),lpad(p.ID_DENOMINATION_GEO,4,'0')) id_siqo,
          p.ID_APPELLATION id_app,
          p.ID_DENOMINATION_GEO id_denom,
          ta.app_libelle appellation,
          d.DEN_GEO_LIBELLE denomination,
          group_concat(DISTINCT p.pro_libelle_produit ORDER BY p.pro_libelle_produit ASC separator ', ') produit,
          group_concat(DISTINCT cp.CAT_PRO_LIBELLE ORDER BY cp.CAT_PRO_LIBELLE ASC separator ', ') categorie,
          group_concat(DISTINCT left(s.STA_LIBELLE,3) ORDER BY  s.STA_LIBELLE ASC separator ', ') signe,
          group_concat(DISTINCT p.pro_id_cvi ORDER BY p.pro_id_cvi ASC separator ', ') lst_id_cvi,
          group_concat(DISTINCT tci.cen_ina_nom ORDER BY tci.cen_ina_nom ASC separator ',') lst_centre
      FROM t_produit p
      LEFT JOIN t_denomination_geo d ON p.ID_DENOMINATION_GEO = d.ID_DENOMINATION_GEO
      LEFT JOIN t_categorie_produit cp ON p.ID_CATEGORIE_PRODUIT= cp.ID_CATEGORIE_PRODUIT
      LEFT JOIN t_statut s ON p.ID_STATUT = s.ID_STATUT
      LEFT JOIN l_produit_centre_inao lpc ON p.id_produit = lpc.id_produit
      LEFT JOIN t_centre_inao tci ON lpc.id_centre_inao = tci.ID_CENTRE_INAO
      LEFT JOIN t_statut ts ON p.id_statut = ts.id_statut
      LEFT JOIN t_appellation ta ON ta.id_appellation = p.id_appellation
      WHERE p.PRO_DATE_ARCHIVAGE = 0
      AND p.pro_etat = 2
      GROUP BY
          p.ID_APPELLATION,
          p.ID_DENOMINATION_GEO,
          d.DEN_GEO_LIBELLE
    RESULT -> t_siqo (writer POSTGRES_2)
    RESULT -> SQLCreator_Result
SQLCreator_Result: Inspector
t_siqo (writer POSTGRES_2)
    attributes: id_siqo varchar(8),PrimaryKey, id_app int4,BTree, appellation text, id_denom int4,BTree, denomination text, produit text, categorie text, signe text, lst_centre text, lst_id_cvi text
SQLCreator_2 [off]
    DATASET = bsi inao
    EXPOSED_ATTRIBUTE_LIST = air_geo_libelle,aire_geo_cvi,Appellation,Categorie,"Classe UE",DEN_GEO_TYPE_APPELLATION,Denomination,id_aire_geographique,id_appellation,ID_CATEGORIE_PRODUIT,id_denomination_geo,ID_TYPE_PRODUIT,Lib_etat,pro_etat,"Signe FR","Signe UE",Site,DT
    FORMAT = MYSQL
    MYSQL_HANDLE_UTC_OFFSET = Yes
    MYSQL_NAMED_CONNECTION = bsi inao
    MYSQL_QUERY_FEATURE_TYPES_FOR_MERGE_FILTERS = Yes
    SQL_STATEMENT:
      SELECT DISTINCT
          LEFT(TS.STA_LIBELLE,5) as "Signe FR" ,
          LEFT(TS2.STA_LIBELLE,5) as "Signe UE" ,
          t_categorie_produit.ID_CATEGORIE_PRODUIT,
          t_categorie_produit.CAT_PRO_LIBELLE as "Categorie",
          t_type_produit.ID_TYPE_PRODUIT,
          t_type_produit.TYP_PRO_LIBELLE as "Classe UE",
          t_appellation.id_appellation,
          t_appellation.APP_LIBELLE as "Appellation",
          t_denomination_geo.id_denomination_geo,
          t_denomination_geo.DEN_GEO_LIBELLE as "Denomination",
          t_denomination_geo.DEN_GEO_TYPE_APPELLATION,
          t_aire_geographique.id_aire_geographique,
          t_aire_geographique.air_geo_libelle,
          concat(left(t_produit.pro_id_cvi,1),
          mid(t_produit.pro_id_cvi,3,3)) as aire_geo_cvi,
          t_produit.pro_etat,
          (CASE t_produit.PRO_ETAT WHEN 1 THEN "En cours" WHEN 2 THEN "Publié" ELSE "" END) as "Lib_etat",
          t_centre_inao.CEN_INA_NOM as "Site",
          t_centre_inao.CEN_INA_ADRESSE_1 as "DT"
      FROM
          t_appellation
          INNER JOIN t_produit ON t_produit.ID_APPELLATION=t_appellation.ID_APPELLATION
          INNER JOIN t_denomination_geo ON t_produit.ID_DENOMINATION_GEO=t_denomination_geo.ID_DENOMINATION_GEO
          INNER JOIN t_aire_geographique ON t_aire_geographique.ID_AIRE_GEOGRAPHIQUE=t_produit.ID_AIRE_GEOGRAPHIQUE
          LEFT OUTER JOIN l_produit_centre_inao ON t_produit.ID_PRODUIT=l_produit_centre_inao.ID_PRODUIT
          INNER JOIN t_centre_inao ON t_centre_inao.ID_CENTRE_INAO=l_produit_centre_inao.ID_CENTRE_INAO
          LEFT JOIN t_statut AS TS ON TS.id_statut=t_produit.id_statut
          LEFT JOIN t_statut AS TS2 ON TS2.id_statut=t_produit.id_statut_ce
          LEFT OUTER JOIN t_categorie_produit ON t_produit.ID_CATEGORIE_PRODUIT=t_categorie_produit.ID_CATEGORIE_PRODUIT
          INNER JOIN t_type_produit ON t_type_produit.ID_TYPE_PRODUIT=t_categorie_produit.ID_TYPE_PRODUIT
      WHERE
          t_produit.PRO_DATE_ARCHIVAGE=0
          and t_produit.PRO_ETAT=2
          and t_type_produit.TYP_PRO_LIBELLE = 'Vins'
      ORDER BY 1, 2, 3

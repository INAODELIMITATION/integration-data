FME workspace add_siqo_link.fmw

Parameters:
- DestDataset_POSTGRES = srv_sig_1   # Connection

Writers:
- POSTGRES_1: POSTGRES to $(DestDataset_POSTGRES)

SQLCreator
    DATASET = bsi inao
    EXPOSED_ATTRIBUTE_LIST = "Classe UE",Date_Texte_Consolide,DEN_GEO_LIBELLE,Etape,ID_APPELLATION,ID_DENOMINATION_GEO,ID_TEXTE_CONSOLIDE,ID_TYPE_PRODUIT,Info,LienCDC,LienPageTexteReglementaire,"Signe CE","Signe FR",Texte,ThÃ¨me
    FORMAT = MYSQL
    MYSQL_NAMED_CONNECTION = bsi inao
    MYSQL_QUERY_FEATURE_TYPES_FOR_MERGE_FILTERS = Yes
    SQL_STATEMENT:
      SELECT DISTINCT
      	LEFT(TS.STA_LIBELLE,5) as "Signe FR",
      	LEFT(TS2.STA_LIBELLE,5) as "Signe CE",
      	t_type_produit.ID_TYPE_PRODUIT,
      	t_type_produit.TYP_PRO_LIBELLE as "Classe UE",
      	TP.ID_APPELLATION, TD.ID_DENOMINATION_GEO,
      	TD.DEN_GEO_LIBELLE, left(TC.TEX_CON_DATE,10) as "Date_Texte_Consolide",
      	TT.THE_LIBELLE as "Thème",
      	TE.ETA_TEX_LIBELLE as "Etape",
      	TC.TEX_CON_TITRE as "Texte",
      	TC.ID_TEXTE_CONSOLIDE,
      	concat("https://www.inao.gouv.fr/show_texte/", TC.ID_TEXTE_CONSOLIDE) AS "LienPageTexteReglementaire",
      	CONCAT(LEFT(TJ.TEX_JO_LIBELLE,6), TT.ID_THEME, TE.ID_ETAPE_TEXTE) as "Info",
      	(CASE CONCAT(LEFT(TJ.TEX_JO_LIBELLE,6), TT.ID_THEME, TE.ID_ETAPE_TEXTE) WHEN "Cahier72" THEN TJ.TEX_JO_LEGIFRANCE ELSE "" END) AS "LienCDC"
      FROM t_texte_consolide AS TC LEFT JOIN t_theme AS TT ON TC.ID_THEME=TT.ID_THEME
      LEFT JOIN t_etape_texte AS TE ON TC.ID_ETAPE_TEXTE=TE.ID_ETAPE_TEXTE
      INNER JOIN l_jo_consolide AS LJ ON TC.id_texte_consolide=LJ.id_texte_consolide
      INNER JOIN t_texte_jo AS TJ on LJ.id_texte_jo=TJ.id_texte_jo
      INNER JOIN l_produit_regles_txtconsolide AS LR ON TC.ID_TEXTE_CONSOLIDE=LR.ID_TEXTE_CONSOLIDE
      INNER JOIN t_produit AS TP ON LR.ID_PRODUIT=TP.ID_PRODUIT
      INNER JOIN t_denomination_geo AS TD ON TP.ID_DENOMINATION_GEO=TD.ID_DENOMINATION_GEO
      INNER JOIN t_fiche_descriptive AS TF ON TP.ID_FICHE_DESCRIPTIVE=TF.ID_FICHE_DESCRIPTIVE
      LEFT JOIN l_fiche_groupement as LFG ON LFG.ID_FICHE_DESCRIPTIVE=TF.ID_FICHE_DESCRIPTIVE
      LEFT JOIN t_groupement_demandeur as GD ON GD.ID_GROUPEMENT_DEMANDEUR=LFG.ID_GROUPEMENT_DEMANDEUR
      LEFT JOIN t_statut AS TS ON TS.id_statut=TP.id_statut
      LEFT JOIN t_statut AS TS2 ON TS2.id_statut=TP.id_statut_ce
      LEFT OUTER JOIN t_categorie_produit ON TP.ID_CATEGORIE_PRODUIT=t_categorie_produit.ID_CATEGORIE_PRODUIT
      INNER JOIN t_type_produit ON t_type_produit.ID_TYPE_PRODUIT=t_categorie_produit.ID_TYPE_PRODUIT
      WHERE TP.PRO_DATE_ARCHIVAGE=0
      AND TP.PRO_ETAT=2
      AND TC.TEX_CON_ETAT="1"
      ORDER BY 1,2,3,5,4,6
    RESULT -> BulkAttributeRenamer
BulkAttributeRenamer
    ATTRCHOICE = All Attributes
    CASE_CHANGE_TYPE = lower
    MODE_CHOICE = RENAME
    PATTERN_ACTION_DISP = CASECHANGE
    -> AttributeManager
AttributeManager
    ATTR_TABLE:
      RENAME_SET_VALUE id_appellation > id_app
      RENAME_SET_VALUE id_denomination_geo > id_denom
      RENAME_SET_VALUE den_geo_libelle > lbl_denomination
      RENAME_SET_VALUE signe ce > signe_ce
      RENAME_SET_VALUE signe fr > signe_fr
      RENAME_SET_VALUE thã¨me > theme
    -> StringFormatter
StringFormatter
    FORMAT = 04s
    SRC_ATTRS = id_denom,id_app
    -> StringConcatenator
StringConcatenator
    ACTION = Create New Attribute
    PARM_LINE = @Value(id_app)@Value(id_denom)
    VAL_ATTR = id_siqo
    -> SQLExecutor [INITIATOR]
SQLExecutor
    COMBINE_ATTRS = Keep Initiator Attributes if Conflict
    COMBINE_GEOM = Initiator Geometry Only
    DATASET = srv_sig_1
    EXPOSED_ATTRIBUTE_LIST = id_aire
    FORMAT = POSTGRES
    POSTGRES_NAMED_CONNECTION = srv_sig_1
    POSTGRES_QUERY_FEATURE_TYPES_FOR_MERGE_FILTERS = Yes
    POSTGRES_READ_TIME_WITH_TIMEZONE = Yes
    POSTGRES_SCHEMAS_FOR_TABLE_LISTING = edigeo ign_bd_cadastre ign_bd_carto ign_bd_topo mae metier_inao work cvi etalab
    SQL_STATEMENT:
      SELECT "id_aire"
      FROM "metier_inao"."t_aire"
      WHERE "id_siqo" = '@Value(id_siqo)'
    RESULT -> AttributeManager_2
AttributeManager_2
    ATTR_TABLE:
      RENAME_SET_VALUE liencdc > lien_cdc
      RENAME_SET_VALUE lienpagetextereglementaire > lien_reglement
    -> t_siqo_link (writer POSTGRES_1)
t_siqo_link (writer POSTGRES_1)
    attributes: id_siqo text, id_app varchar(200), id_denom varchar(200), id_aire int8, id_texte_consolide varchar(200), id_type_produit varchar(200), classe_ue varchar(200), date_texte_consolide varchar(200), etape varchar(200), lbl_denomination varchar(200), info varchar(200), lien_cdc varchar(200), lien_reglement text, signe_ce text, signe_fr text, texte text, theme text
SQLCreator_2
    DATASET = srv_sig_1
    FORMAT = POSTGRES
    POSTGRES_NAMED_CONNECTION = srv_sig_1
    POSTGRES_QUERY_FEATURE_TYPES_FOR_MERGE_FILTERS = Yes
    POSTGRES_SCHEMAS_FOR_TABLE_LISTING = edigeo ign_bd_cadastre ign_bd_carto ign_bd_topo mae metier_inao work cvi etalab
    SQL_STATEMENT:
      SELECT
      FROM

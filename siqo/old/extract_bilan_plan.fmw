FME workspace extract_bilan_plan.fmw

Parameters:
- SourceDataset_XLSXR = $(FME_MF_DIR)bilan_db.xlsx   # Source Microsoft Excel File(s)
- SourceDataset_POSTGRES = srv_sig_1   # Connection
- DestDataset_XLSXW = $(FME_MF_DIR)bilan_bddc.xlsx   # Destination Microsoft Excel File

Readers:
- XLSXR_1: XLSXR from $(SourceDataset_XLSXR)
- POSTGRES_1: POSTGRES from $(SourceDataset_POSTGRES)

Writers:
- XLSXW_1: XLSXW to $(DestDataset_XLSXW)

v_plan_par_commune (reader POSTGRES_1)
    attributes: id_siqo text, id_aire int4, insee text, lbl_aire text, tif_file_date text, tif_file_path_rep text, tif_df text, pdf_file_date text, pdf_file_path_rep text, pdf_df text
    -> AttributeManager
AttributeManager
    -> FeatureMerger [SUPPLIER]
inventaire (reader XLSXR_1)
    attributes: UID number(6,0), siqo_site char(12), siqo_code_insee number(6,0), siqo_nom_com char(28), siqo_id_app number(5,0), siqo_appellation char(24), siqo_id_denom number(5,0), siqo_denomination char(35), etat_general char(26), etat_db char(11), inv_cp number(9,0), inv_np char(11), inv_agent char(11), commentaire char(55), file_name string
    -> BulkAttributeRenamer
BulkAttributeRenamer
    ATTRCHOICE = All Attributes
    CASE_DISP = YES
    MODE_CHOICE = RENAME
    PATTERN_ACTION_DISP = REMOVEPREFIX
    REPLACE_STR = siqo_
    -> AttributeManager_2
AttributeManager_2
    ATTR_TABLE:
      REMOVE UID
      RENAME_SET_VALUE code_insee > insee
      REMOVE file_name
    -> FeatureMerger [REQUESTOR]
FeatureMerger
    ATTR_ACCUM_MODE = Merge Supplier
    ATTR_CONFLICT_RES = Use Requestor
    IGNORE_NULLS = No
    JOIN_KEYS = @Value(insee) @Value(insee) STRING @Value(id_denom) @int(@Right(@Value(id_siqo),4)) NUM
    MERGE_TYPE = Attributes Only
    PROCESS_DUPS = NO
    REJECT_NULL_MISSING_KEYS = No
    SUPPLIERS_FIRST = No
    MERGED -> bilan (writer XLSXW_1)
    UNMERGED_REQUESTOR -> bilan (writer XLSXW_1)
    UNUSED_SUPPLIER -> plan_non_trouve (writer XLSXW_1)
bilan (writer XLSXW_1)
    attributes: id_siqo string(20), id_aire number(20), lbl_aire string(20), site auto(20), insee string(20), nom_com auto(20), id_app auto(20), appellation auto(20), id_denom auto(20), denomination auto(20), etat_general string(26), etat_db string(11), inv_cp string(9), inv_np string(11), inv_agent string(11), commentaire string(55), tif_file_date date(20), tif_file_path_rep string(20), tif_df string(20), pdf_file_date date(20), pdf_file_path_rep string(20), pdf_df string(20)
plan_non_trouve (writer XLSXW_1)
    attributes: id_siqo string(20), id_aire number(20), insee string(20), lbl_aire string(20), tif_file_date string(20), tif_file_path_rep string(20), tif_df string(20), pdf_file_date string(20), pdf_file_path_rep string(20), pdf_df string(20)

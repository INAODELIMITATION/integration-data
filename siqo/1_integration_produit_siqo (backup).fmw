FME workspace 1_integration_produit_siqo (backup).fmw

Parameters:
- SourceDataset_POSTGRES = srv_sig_1   # Connection
- DestDataset_POSTGRES = srv_sig_1   # Connection

Readers:
- POSTGRES_1: POSTGRES from $(SourceDataset_POSTGRES)

Writers:
- POSTGRES_2: POSTGRES to $(DestDataset_POSTGRES)

Note: requete les denomination dans la base SIQO
SQLCreator
    DATASET = bsi inao
    EXPOSED_ATTRIBUTE_LIST = id_siqo,id_app,appellation,id_denom,denomination,produit,categorie,signe,lst_centre,lst_id_cvi
    FORMAT = MYSQL
    MYSQL_NAMED_CONNECTION = bsi inao
    MYSQL_QUERY_FEATURE_TYPES_FOR_MERGE_FILTERS = Yes
    SQL_STATEMENT:
      SELECT DISTINCT
          concat(lpad(p.ID_APPELLATION,4,'0'),lpad(p.ID_DENOMINATION_GEO,4,'0')) id_siqo,
          p.ID_APPELLATION id_app,
          p.ID_DENOMINATION_GEO id_denom,
          ta.app_libelle appellation,
          d.DEN_GEO_LIBELLE denomination,
          group_concat(DISTINCT p.pro_libelle_produit ORDER BY p.pro_libelle_produit ASC separator ', ') produit,
          group_concat(DISTINCT cp.CAT_PRO_LIBELLE ORDER BY cp.CAT_PRO_LIBELLE ASC separator ', ') categorie,
          group_concat(DISTINCT left(s.STA_LIBELLE,3) ORDER BY  s.STA_LIBELLE ASC separator ', ') signe,
          group_concat(DISTINCT p.pro_id_cvi ORDER BY p.pro_id_cvi ASC separator ', ') lst_id_cvi,
          group_concat(DISTINCT tci.cen_ina_nom ORDER BY tci.cen_ina_nom ASC separator ',') lst_centre
      FROM t_produit p
      LEFT JOIN t_denomination_geo d ON p.ID_DENOMINATION_GEO = d.ID_DENOMINATION_GEO
      LEFT JOIN t_categorie_produit cp ON p.ID_CATEGORIE_PRODUIT= cp.ID_CATEGORIE_PRODUIT
      LEFT JOIN t_statut s ON p.ID_STATUT = s.ID_STATUT
      LEFT JOIN l_produit_centre_inao lpc ON p.id_produit = lpc.id_produit
      LEFT JOIN t_centre_inao tci ON lpc.id_centre_inao = tci.ID_CENTRE_INAO
      LEFT JOIN t_statut ts ON p.id_statut = ts.id_statut
      LEFT JOIN t_appellation ta ON ta.id_appellation = p.id_appellation
      WHERE p.PRO_DATE_ARCHIVAGE = 0
      AND p.pro_etat = 2
      GROUP BY
          p.ID_APPELLATION,
          p.ID_DENOMINATION_GEO,
          d.DEN_GEO_LIBELLE
    RESULT -> t_siqo (writer POSTGRES_2)
    RESULT -> SQLCreator_Result
SQLCreator_Result: Inspector
t_siqo (writer POSTGRES_2)
    attributes: id_siqo varchar(8),PrimaryKey, id_app int4,BTree, appellation text, id_denom int4,BTree, denomination text, produit text, categorie text, signe text, lst_centre text, lst_id_cvi text

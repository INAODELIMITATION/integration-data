FME workspace bdsiqo_bdsig_compare.fmw

Parameters:
- SourceDataset_POSTGRES = srv_sig_1   # Connection

Readers:
- POSTGRES_1: POSTGRES from $(SourceDataset_POSTGRES)

Note: requete les denomination dans la base SIQO
SQLCreator
    DATASET = bsi inao
    EXPOSED_ATTRIBUTE_LIST = categorie,denomination,id_app,id_denom,id_siqo,lst_id_cvi,signe
    FORMAT = MYSQL
    MYSQL_NAMED_CONNECTION = bsi inao
    MYSQL_QUERY_FEATURE_TYPES_FOR_MERGE_FILTERS = Yes
    SQL_STATEMENT:
      SELECT DISTINCT
          concat(p.`ID_APPELLATION`,p.`ID_DENOMINATION_GEO`) id_siqo,
          p.`ID_APPELLATION` id_app,
          p.`ID_DENOMINATION_GEO` id_denom,
          d.`DEN_GEO_LIBELLE` denomination,
          group_concat(DISTINCT cp.`CAT_PRO_LIBELLE` ORDER BY cp.`CAT_PRO_LIBELLE` ASC separator ', ') categorie,
          group_concat(DISTINCT s.`STA_LIBELLE` ORDER BY  s.`STA_LIBELLE` ASC separator ', ') signe,
          group_concat(DISTINCT p.pro_id_cvi ORDER BY p.pro_id_cvi ASC separator ', ') lst_id_cvi
      FROM `t_produit` p
      INNER JOIN `t_denomination_geo` d ON p.`ID_DENOMINATION_GEO` = d.`ID_DENOMINATION_GEO`
      LEFT JOIN `t_categorie_produit` cp ON p.`ID_CATEGORIE_PRODUIT`= cp.`ID_CATEGORIE_PRODUIT`
      LEFT JOIN `t_statut` s ON p.`ID_STATUT` = s.`ID_STATUT`
      WHERE p.`PRO_DATE_ARCHIVAGE` = 0
      AND p.`PRO_ETAT` = 2
      GROUP BY
          p.`ID_APPELLATION` ,
          p.`ID_DENOMINATION_GEO` ,
          d.`DEN_GEO_LIBELLE`
    RESULT -> FeatureMerger [SUPPLIER]
siqo_produit (reader POSTGRES_1)
    attributes: id_app text, appellation text, id_denom text, denomination text, id_prod text, produit text, id_aire_geo varchar(200), id_cvi text, geom_exist bool, id serial,PrimaryKey, id_sig_aire_geo int4, geom_airegeo_exist bool, geom_airepar_exist bool
    -> FeatureMerger [REQUESTOR]
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(id_app) @Value(id_app) AUTO @Value(id_denom) @Value(id_denom) AUTO
    MERGE_TYPE = Attributes Only
    PROCESS_DUPS = YES
    REJECT_NULL_MISSING_KEYS = No
    SUPPLIERS_FIRST = No

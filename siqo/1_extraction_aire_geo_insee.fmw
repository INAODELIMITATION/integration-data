FME workspace 1_extraction_aire_geo_insee.fmw

Parameters:
- SourceDataset_POSTGRES = srv_sig_1   # Connection
- DestDataset_XLSXW = C:\Users\baussier\Desktop\inventaire_dt_ouest.xlsx   # Destination Microsoft Excel File

Readers:
- POSTGRES_1: POSTGRES from $(SourceDataset_POSTGRES)

Writers:
- XLSXW_1: XLSXW to $(DestDataset_XLSXW)

SQLCreator_2
    DATASET = bsi inao
    EXPOSED_ATTRIBUTE_LIST = appellation,centre,code_insee,denomination,DT,id_app,id_denom,nom_com
    FORMAT = MYSQL
    MYSQL_HANDLE_UTC_OFFSET = Yes
    MYSQL_NAMED_CONNECTION = bsi inao
    MYSQL_QUERY_FEATURE_TYPES_FOR_MERGE_FILTERS = Yes
    SQL_STATEMENT:
      SELECT DISTINCT t_commune.COM_CCOM AS "code_insee",
                      t_commune.COM_NCC AS "nom_com",
                      t_appellation.ID_APPELLATION AS "id_app",
                      t_appellation.app_libelle AS "appellation",
                      t_denomination_geo.id_denomination_geo AS "id_denom",
                      t_denomination_geo.DEN_GEO_LIBELLE AS "denomination",
                      t_centre_inao.CEN_INA_NOM as "centre",
                      t_centre_inao.CEN_INA_ADRESSE_1 as "DT"
      FROM t_produit
                     JOIN l_produit_centre_inao ON t_produit.ID_PRODUIT = l_produit_centre_inao.ID_PRODUIT
                     JOIN t_centre_inao ON l_produit_centre_inao.ID_CENTRE_INAO = t_centre_inao.ID_CENTRE_INAO
                     JOIN t_statut ON  t_produit.id_statut = t_statut.id_statut
                     JOIN t_denomination_geo ON t_produit.ID_DENOMINATION_GEO = t_denomination_geo.ID_DENOMINATION_GEO
                     JOIN t_appellation ON t_appellation.id_appellation = t_produit.id_appellation
                     JOIN t_categorie_produit ON t_produit.ID_CATEGORIE_PRODUIT =  t_categorie_produit.ID_CATEGORIE_PRODUIT
                     JOIN t_type_produit ON t_categorie_produit.ID_TYPE_PRODUIT = t_type_produit.ID_TYPE_PRODUIT
                     JOIN t_aire_geographique ON t_produit.ID_AIRE_GEOGRAPHIQUE = t_aire_geographique.ID_AIRE_GEOGRAPHIQUE
                     JOIN l_commune_aire_geo ON t_aire_geographique.ID_aire_geographique = l_commune_aire_geo.ID_aire_geographique
                     JOIN t_commune ON l_commune_aire_geo.ID_COMMUNE = t_commune.ID_COMMUNE
      WHERE
          t_produit.PRO_DATE_ARCHIVAGE = 0
          AND t_produit.PRO_ETAT = 2
          AND t_centre_inao.CEN_INA_ADRESSE_1 like '%ouest%'
      ORDER BY 1, 6
    RESULT -> commune (writer XLSXW_1)
    RESULT -> FeatureMerger [SUPPLIER]
commune (writer XLSXW_1)
    attributes: DT auto(20), centre auto(20), code_insee auto(20), nom_com auto(20), id_app auto(20), appellation auto(20), id_denom auto(20), denomination auto(20)
SQLCreator_3
    DATASET = bsi inao
    EXPOSED_ATTRIBUTE_LIST = appellation,categorie,centre,denomination,DT,id_app,id_denom,type,produit
    FORMAT = MYSQL
    MYSQL_HANDLE_UTC_OFFSET = Yes
    MYSQL_NAMED_CONNECTION = bsi inao
    MYSQL_QUERY_FEATURE_TYPES_FOR_MERGE_FILTERS = Yes
    SQL_STATEMENT:
      SELECT DISTINCT

                      t_appellation.ID_APPELLATION AS "id_app",
                      t_appellation.app_libelle AS "appellation",
                      t_denomination_geo.id_denomination_geo AS "id_denom",
                      t_denomination_geo.DEN_GEO_LIBELLE AS "denomination",
                      t_categorie_produit.CAT_PRO_LIBELLE categorie,
                      t_type_produit.typ_pro_libelle type,
                      t_centre_inao.CEN_INA_NOM as "centre",
                      t_centre_inao.CEN_INA_ADRESSE_1 as "DT"
      FROM t_produit
                     JOIN l_produit_centre_inao ON t_produit.ID_PRODUIT = l_produit_centre_inao.ID_PRODUIT
                     JOIN t_centre_inao ON l_produit_centre_inao.ID_CENTRE_INAO = t_centre_inao.ID_CENTRE_INAO
                     JOIN t_denomination_geo ON t_produit.ID_DENOMINATION_GEO = t_denomination_geo.ID_DENOMINATION_GEO
                     JOIN t_appellation ON t_appellation.id_appellation = t_produit.id_appellation
                     JOIN t_categorie_produit ON t_produit.ID_CATEGORIE_PRODUIT =  t_categorie_produit.ID_CATEGORIE_PRODUIT
                     JOIN t_type_produit ON t_categorie_produit.ID_TYPE_PRODUIT = t_type_produit.ID_TYPE_PRODUIT
      WHERE
          t_produit.PRO_DATE_ARCHIVAGE = 0
          AND t_produit.PRO_ETAT = 2
          AND t_centre_inao.CEN_INA_ADRESSE_1 like '%ouest%'
          AND (t_appellation.app_libelle not like '%--STG%' and t_appellation.app_libelle not like '%--LR%')
      ORDER BY 1, 6
    RESULT -> FeatureMerger [REQUESTOR]
FeatureMerger
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(id_app) @Value(id_app) AUTO @Value(id_denom) @Value(id_denom) AUTO
    MERGE_TYPE = Attributes Only
    PROCESS_DUPS = YES
    REJECT_NULL_MISSING_KEYS = No
    SUPPLIERS_FIRST = No
    MERGED -> AttributeCreator_2
    UNMERGED_REQUESTOR -> AttributeCreator
AttributeCreator_2
    ATTR_TABLE = SET_TO liste_com_siqo = oui
    -> produit (writer XLSXW_1)
    -> AttributeCreator_Output
AttributeCreator
    ATTR_TABLE = SET_TO liste_com_siqo = non
    -> produit (writer XLSXW_1)
    -> AttributeCreator_Output
produit (writer XLSXW_1)
    attributes: DT auto(20), centre auto(20), type auto(20), categorie auto(20), id_app auto(20), appellation auto(20), id_denom auto(20), denomination auto(20), produit auto(20), liste_com_siqo auto(20)
AttributeCreator_Output: Inspector

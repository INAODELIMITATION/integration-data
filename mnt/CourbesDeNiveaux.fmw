FME workspace CourbesDeNiveaux.fmw

Parameters:
- SourceDataset_ESRIASCIIGRID = ""C:\Users\baussier\Desktop\RGEALTI_2-0_5M_ASC_LAMB93-IGN69_D084_2016-02-03\RGEALTI\1_DONNEES_LIVRAISON_2016-03-00227\RGEALTI_MNT_5M_ASC_LAMB93_IGN69_D084\**\*.asc" "C:\Users\baussier\Desktop\RGEALTI_2-0_5M_ASC_LAMB93-IGN69_D084_2016-02-03\RGEALTI\1_DONNEES_LIVRAISON_2016-03-00227\RGEALTI_MNT_5M_ASC_LAMB93_IGN69_D084\*.grd""   # Fichier(s) ESRI ASCII Grid Source 
- COORDSYS = EPSG:2154   # COORDSYS SYSTEME COODONNEES SOURCES 
- CONTOUR_INTERVAL = 5   # INTERVALLES DES COURBES DE NIVEAU
- COORDSYS_2 = EPSG:2154   # SYSTEME COORDONNEES DESTINATION MAPINFO 
- DestDataset_MITAB = C:\Users\baussier\Desktop\courbes   # REPERTOIRE DESTINATION MAPINFO 
- TOLERANCE = 1   # PRECISION ALTIMETRIQUE 
- HEIGHT = 16   # HAUTEUR DU LABEL COURN DE NIVEAU 
- DIST = 3   # ELOIGNEMENT DU LABEL / COURBE DE NIVEAU 

Readers:
- ESRIASCIIGRID_1: ESRIASCIIGRID from $(SourceDataset_ESRIASCIIGRID) in $(COORDSYS)

Writers:
- MITAB_1: MITAB to $(DestDataset_MITAB) in $(COORDSYS_2)

Note: Attention avec le format asc / sélectionner tous les fichiers / d'un répertoire sans regroupement / des entités. préparer à l'avance e répertoire / avec les bons fichiers ASC / pas de gestion du nb entité à lire / donc faire 1 test avec 1 seul fichier asc selectionné
ESRIASCIIGRID (reader ESRIASCIIGRID_1)
    -> SurfaceModeller [POINTS]
GeometryFilter
    GEOM_PORT_NAMES = Line
    BREAK_AGG = No
    LINE -> nouvelle_generation_courbniv (writer MITAB_1)
nouvelle_generation_courbniv (writer MITAB_1)
    attributes: _elevation integer,indexed
nouvelle_generation_label_courbniv (writer MITAB_1)
    attributes: _elevation integer,indexed

Bookmark: génération des courbes de niveaux lissées
Note: générer les / courbes de niveaux
SurfaceModeller
    CONTOUR_DIMENSION = 3
    INTERPOLATION_TYPE = AUTO
    NODATA_VALUE = -32767.0
    CONTOUR_INTERVAL = $(CONTOUR_INTERVAL)
    USE_SURFACE_MODEL_FILE = No
    MAX_DIST_FACTOR = 0.0
    IGNORE_INPUT_ON_INTERVAL = Yes
    TOLERANCE = $(TOLERANCE)
    X_SPACING = 25
    ELEV_ATTR = _elevation
    Y_SPACING = 25
    DRAPE_TYPE = VERTEX
    CONTOURS -> LineJoiner
Note: assembler les lignes qui / se touchent de même altitude
LineJoiner
    PRESERVE = no
    CONSIDER_NODE_ELEVATION = no
    TOPOLOGY = End noded
    GROUP_BREAK = no
    BREAK = no
    GROUP_BY = _elevation
    LINE -> Generalizer
Note: lissage des lignes / avec choix algorythme / de lissage
Generalizer
    PRESERVE = Yes
    ALG_TEXT = NURBfit (Smooth)
    SEGMENT_LENGTH = 10
    DEGREE = 2
    -> Labeller
    -> ExpressionEvaluator

Bookmark: Différenciation visuelle
Note: Modulo : Division de l'altitude par une valeur par ex 50 / et examen du reste, Résult est le nombre de / chiffres après la virgule obtenu après la division. / Si ce resultat est 0 cela signifie que l'élévation / est un multiple de N
ExpressionEvaluator
    VAL_ATTR = _result
    EXPRESSION = (@Value(_elevation)%25)
    -> Tester
Note: Si result = 0 / alors multiple de N
Tester
    TEST_LIST = &_result,=,0
    BOOL_OP = OR
    TEST_MODE = Automatic
    TEST_CLAUSE = TEST @Value(_result) = 0
    PASSED -> AttributeCreator
    FAILED -> AttributeCreator_2
Note: Réglage épaisseur et couleur pas de paramétrage / le faire dans le projet
AttributeCreator
    ATTR_LIST = mapinfo_pen_width,2,autocad_lineweight,2,fme_color,0.501960784313725,0.250980392156863,0
    -> GeometryFilter
AttributeCreator_2
    ATTR_LIST = mapinfo_pen_width,0,autocad_lineweight,0,fme_color,0.501960784313725,0.250980392156863,0
    -> GeometryFilter

Bookmark: génération de toponyme
Note: génération des étiquettes
Labeller
    SPACE = 500
    LABATTR = _elevation
    TANROTATTR = _label_rotation
    DIST = $(DIST)
    ENDS = yes
    HEIGHT = $(HEIGHT)
    MIN = 0
    AVERAGE_CHAR_WIDTH = 0.0
    OVERLAPS = Yes
    SPOT_CHOICE = Above or Right
    PARROTATTR = _parallel_rotation
    LABEL -> AttributeCreator_3
Note: coloration marron
AttributeCreator_3
    ATTR_LIST = fme_color,0.501960784313725,0.250980392156863,0
    -> nouvelle_generation_label_courbniv (writer MITAB_1)

FME workspace integration_cvi.fmw

Parameters:
- SourceDataset_XML = ""$(FME_MF_DIR)CVI\2017-12-14-Foncier\DGDDI_FONCIER_20171213142905_9_9.xml" "$(FME_MF_DIR)CVI\2017-12-14-Foncier\DGDDI_FONCIER_20171213142905_8_9.xml" "$(FME_MF_DIR)CVI\2017-12-14-Foncier\DGDDI_FONCIER_20171213142905_7_9.xml" "$(FME_MF_DIR)CVI\2017-12-14-Foncier\DGDDI_FONCIER_20171213142905_6_9.xml" "$(FME_MF_DIR)CVI\2017-12-14-Foncier\DGDDI_FONCIER_20171213142905_5_9.xml" "$(FME_MF_DIR)CVI\2017-12-14-Foncier\DGDDI_FONCIER_20171213142905_4_9.xml" "$(FME_MF_DIR)CVI\2017-12-14-Foncier\DGDDI_FONCIER_20171213142905_3_9.xml" "$(FME_MF_DIR)CVI\2017-12-14-Foncier\DGDDI_FONCIER_20171213142905_2_9.xml" "$(FME_MF_DIR)CVI\2017-12-14-Foncier\DGDDI_FONCIER_20171213142905_1_9.xml""   # Source XML File(s)
- FEATURE_TYPES =
- DestDataset_POSTGRES = srv_sig_1   # Connection
- SourceDataset_XML_5 = ""$(FME_MF_DIR)CVI\2017-12-14-Foncier\DGDDI_EVV_20171110153925_2_2.xml" "$(FME_MF_DIR)CVI\2017-12-14-Foncier\DGDDI_EVV_20171110153925_1_2.xml""   # Source XML File(s)
- FEATURE_TYPES_2 =
- DestDataset_POSTGRES_5 = srv_sig_1   # Connection
- SourceDataset_XML_7 = ""$(FME_MF_DIR)CVI\2017-12-14-Foncier\DGDDI_PPM_20171110153218_2_2.xml" "$(FME_MF_DIR)CVI\2017-12-14-Foncier\DGDDI_PPM_20171110153218_1_2.xml""   # Source XML File(s)
- FEATURE_TYPES_3 =
- DestDataset_POSTGRES_7 = srv_sig_1   # Connection
- SourceDataset_XML_6 = $(FME_MF_DIR)CVI\2017-09-25-Recoltes\DGDDI_RECOLTE_20170829134418_1_1.xml   # Source XML File(s)
- FEATURE_TYPES_4 =
- DestDataset_POSTGRES_6 = srv_sig_1   # Connection

Readers:
- XML_1: XML from $(SourceDataset_XML)
- XML_2: XML from $(SourceDataset_XML_5)
- XML_3: XML from $(SourceDataset_XML_7)
- XML_4: XML from $(SourceDataset_XML_6)

Writers:
- POSTGRES_1: POSTGRES to $(DestDataset_POSTGRES)
- POSTGRES_2: POSTGRES to $(DestDataset_POSTGRES_5)
- POSTGRES_3: POSTGRES to $(DestDataset_POSTGRES_7)
- POSTGRES_4: POSTGRES to $(DestDataset_POSTGRES_6)

Note: EVV
evv (reader XML_2)
    attributes: adresse.codePays xml_char(3), adresse.codePostal xml_char(255), adresse.commune xml_char(255), adresse.complementAdresse xml_char(255), adresse.distributionSpeciale xml_char(255), adresse.ligneAchPostale xml_char(51), adresse.nomPays xml_char(255), adresse.nomVoie xml_char(255), adresse.numeroVoie xml_char(5), adresse.repetition xml_char(10), adresse.typeVoieCourt xml_char(5), adresse.typeVoieLong xml_char(255), bureauInstructeur.codeBureauInstructeur xml_char(15), bureauInstructeur.libelleBureauInstructeur xml_char(27), codeCategorie xml_decimal(2,0), codeEVV xml_char(11), codeEVVPrecedente xml_decimal(11,0), codeInterpro xml_decimal(4,0), codePPM xml_char(10), codeRepresentantLegal xml_decimal(9,0), communeRattachement.codeINSEE xml_char(7), dateChangementActivite xml_char(23), dateCreation xml_char(23), email xml_char(71), etatActivite xml_decimal(2,0), fax xml_char(51), formeActivite xml_decimal(2,0), informatisationCave xml_decimal(2,0), installationsGerees.installationGeree.adresse.codePays xml_char(255), installationsGerees.installationGeree.adresse.codePostal xml_char(255),
      installationsGerees.installationGeree.adresse.commune xml_char(255), installationsGerees.installationGeree.adresse.complementAdresse xml_char(255), installationsGerees.installationGeree.adresse.distributionSpeciale xml_char(255), installationsGerees.installationGeree.adresse.ligneAchPostale xml_char(255), installationsGerees.installationGeree.adresse.nomPays xml_char(255), installationsGerees.installationGeree.adresse.nomVoie xml_char(255), installationsGerees.installationGeree.adresse.numeroVoie xml_char(5), installationsGerees.installationGeree.adresse.repetition xml_char(255), installationsGerees.installationGeree.adresse.typeVoieCourt xml_char(5), installationsGerees.installationGeree.adresse.typeVoieLong xml_char(255), installationsGerees.installationGeree.estPrincipale xml_decimal(2,0), installationsGerees.installationGeree.etatActivite xml_decimal(2,0), installationsGerees.installationGeree.modeVinification xml_decimal(2,0), installationsGerees.installationGeree.numeroIVI xml_char(14), installationsGerees.installationGeree.typeInstallation xml_decimal(2,0), installationsGerees.installationGeree{}.adresse.codePays xml_char(3), installationsGerees.installationGeree{}.adresse.codePostal xml_decimal(6,0), installationsGerees.installationGeree{}.adresse.commune xml_char(255), installationsGerees.installationGeree{}.adresse.complementAdresse xml_char(255), installationsGerees.installationGeree{}.adresse.distributionSpeciale xml_char(255), installationsGerees.installationGeree{}.adresse.ligneAchPostale xml_char(255), installationsGerees.installationGeree{}.adresse.nomPays xml_char(255), installationsGerees.installationGeree{}.adresse.nomVoie xml_char(255), installationsGerees.installationGeree{}.adresse.numeroVoie xml_char(5), installationsGerees.installationGeree{}.adresse.repetition xml_char(255), installationsGerees.installationGeree{}.adresse.typeVoieCourt xml_char(5), installationsGerees.installationGeree{}.adresse.typeVoieLong xml_char(255), installationsGerees.installationGeree{}.estPrincipale xml_decimal(2,0), installationsGerees.installationGeree{}.etatActivite xml_decimal(2,0), installationsGerees.installationGeree{}.modeVinification xml_decimal(2,0),
      installationsGerees.installationGeree{}.numeroIVI xml_char(255), installationsGerees.installationGeree{}.typeInstallation xml_decimal(2,0), libelleEVV xml_char(51), libelleEVVPrecedente xml_char(255), libelleInterpro xml_char(14), libelleOperateur xml_char(51), libellePPM xml_char(255), modesFaireValoir.modeFaireValoir.codeModeFaireValoir xml_char(2), modesFaireValoir.modeFaireValoir{}.codeModeFaireValoir xml_char(2), nomRepresentantLegal xml_char(255), ppmsAyantDelegation.ppmAyantDelegation.codePPM xml_char(10), ppmsAyantDelegation.ppmAyantDelegation{}.codePPM xml_char(10), qualiteDistillateur xml_decimal(2,0), siret xml_decimal(15,0), statutDistillateur xml_decimal(2,0), telephone xml_char(41), typeBailleur xml_decimal(2,0), typeRecoltant xml_decimal(2,0), xml_fragment xml_xml, xml_id xml_char(255), xml_matched_element xml_char(4), xml_parent_child_pos xml_char(1), xml_parent_id xml_char(1)
    -> ListExploder_2
ListExploder_2
    INDEX_ATTR = _element_index
    LIST_ATTR = installationsGerees.installationGeree{}
    ATTR_CONFLICT_RES = Use Incoming List
    ATTR_ACCUM_MODE = Merge Incoming List
    ELEMENTS -> ListExploder_3
    <REJECTED> -> ListExploder_3
ListExploder_3
    INDEX_ATTR = _element_index
    LIST_ATTR = modesFaireValoir.modeFaireValoir{}
    ATTR_CONFLICT_RES = Use Incoming List
    ATTR_ACCUM_MODE = Merge Incoming List
    ELEMENTS -> ListExploder_4
    <REJECTED> -> ListExploder_4
ListExploder_4
    INDEX_ATTR = _element_index
    LIST_ATTR = ppmsAyantDelegation.ppmAyantDelegation{}
    ATTR_CONFLICT_RES = Use Incoming List
    ATTR_ACCUM_MODE = Merge Incoming List
    ELEMENTS -> AttributeRemover
    <REJECTED> -> AttributeRemover
AttributeRemover
    REMOVE_ATTRS = installationsGerees.installationGeree.adresse.complementAdresse,installationsGerees.installationGeree.adresse.nomPays,adresse.repetition,installationsGerees.installationGeree.adresse.commune,installationsGerees.installationGeree.estPrincipale,installationsGerees.installationGeree.adresse.typeVoieLong,installationsGerees.installationGeree.adresse.nomVoie,adresse.codePostal,adresse.codePays,installationsGerees.installationGeree.adresse.repetition,installationsGerees.installationGeree.numeroIVI,adresse.complementAdresse,adresse.nomPays,adresse.nomVoie,adresse.typeVoieCourt,installationsGerees.installationGeree.typeInstallation,modesFaireValoir.modeFaireValoir.codeModeFaireValoir,adresse.numeroVoie,installationsGerees.installationGeree.adresse.ligneAchPostale,adresse.typeVoieLong,installationsGerees.installationGeree.adresse.distributionSpeciale,adresse.ligneAchPostale,ppmsAyantDelegation.ppmAyantDelegation.codePPM,installationsGerees.installationGeree.adresse.numeroVoie,installationsGerees.installationGeree.adresse.codePays,installationsGerees.installationGeree.etatActivite,installationsGerees.installationGeree.adresse.typeVoieCourt,installationsGerees.installationGeree.modeVinification,adresse.distributionSpeciale,installationsGerees.installationGeree.adresse.codePostal,adresse.commune
    -> AttributeManager_3
AttributeManager_3
    ATTR_TABLE:
      RENAME_SET_VALUE bureauInstructeur.codeBureauInstructeur > codeBureauInstructeur
      RENAME_SET_VALUE bureauInstructeur.libelleBureauInstructeur > libelleBureauInstructeur
      RENAME_SET_VALUE communeRattachement.codeINSEE > communeRattachementcodeINSEE
      REMOVE xml_fragment
      REMOVE xml_id
      REMOVE xml_matched_element
      REMOVE xml_parent_child_pos
      REMOVE xml_parent_id
      REMOVE fme_feature_type
      REMOVE fme_rejection_code
      REMOVE _element_index
    -> BulkAttributeRenamer_3
BulkAttributeRenamer_3
    CASE_CHANGE_TYPE = lower
    ATTRCHOICE = All Attributes
    PATTERN_ACTION_DISP = CASECHANGE
    MODE_CHOICE = RENAME
    -> cvi.evv (writer POSTGRES_2)
cvi.evv (writer POSTGRES_2)
    attributes: codebureauinstructeur varchar(200), libellebureauinstructeur varchar(200), codecategorie varchar(200), codeevv varchar(200), codeevvprecedente varchar(200), codeinterpro varchar(200), codeppm varchar(200), coderepresentantlegal varchar(200), communerattachementcodeinsee varchar(200), datechangementactivite varchar(200), datecreation varchar(200), email varchar(71), etatactivite varchar(200), fax varchar(51), formeactivite varchar(200), informatisationcave varchar(200), estprincipale varchar(200), modevinification varchar(200), numeroivi varchar(200), typeinstallation varchar(200), libelleevv varchar(200), libelleevvprecedente varchar(200), libelleinterpro varchar(200), libelleoperateur varchar(200), libelleppm varchar(200), codemodefairevaloir varchar(200), nomrepresentantlegal varchar(200), qualitedistillateur varchar(200), siret int8, statutdistillateur varchar(200),
      telephone varchar(41), typebailleur varchar(200), typerecoltant varchar(200)
prenom (reader XML_3)
    attributes: prenom xml_char(255), xml_fragment xml_xml, xml_id xml_char(21), xml_matched_element xml_char(7), xml_parent_child_pos xml_decimal(2,0), xml_parent_id xml_char(16), adresse.commune xml_char(255), adresse.typeVoieLong xml_char(21), codePPM xml_char(10), dateNaissance xml_char(11), adresse.nomPays xml_char(255), email xml_char(255), etatActivite xml_decimal(2,0), codeRegimeFiscal xml_char(2), typePPM xml_decimal(2,0), libellePPM xml_char(51), adresse.distributionSpeciale xml_char(255), adresse.typeVoieCourt xml_char(5), fax xml_char(255), siren xml_char(10), adresse.ligneAchPostale xml_char(51), qualitesPPM.qualitePPM{}.codeQualite xml_decimal(2,0), adresse.nomVoie xml_char(51), nom xml_char(255), adresse.complementAdresse xml_char(50), adresse.codePostal xml_char(255), adresse.repetition xml_char(10), statutJuridique xml_decimal(2,0), libelleOperateur xml_char(51), adresse.numeroVoie xml_char(5),
      adresse.codePays xml_char(255), qualitesPPM.qualitePPM.codeQualite xml_decimal(2,0), telephone xml_char(41), bureauInstructeur.codeBureauInstructeur xml_char(15), formeJuridique xml_decimal(3,0), bureauInstructeur.libelleBureauInstructeur xml_char(255)
    -> ListExploder_5
ListExploder_5
    INDEX_ATTR = _element_index
    LIST_ATTR = qualitesPPM.qualitePPM{}
    ATTR_CONFLICT_RES = Use Incoming List
    ATTR_ACCUM_MODE = Merge Incoming List
    ELEMENTS -> AttributeRemover_2
    <REJECTED> -> BulkAttributeRenamer_4
AttributeRemover_2
    REMOVE_ATTRS = codeQualite
    -> BulkAttributeRenamer_4
BulkAttributeRenamer_4
    REPLACE_STR = adresse.
    CASE_DISP = YES
    ATTRCHOICE = All Attributes
    PATTERN_ACTION_DISP = REMOVESUFFIX
    MODE_CHOICE = RENAME
    -> BulkAttributeRenamer_5
BulkAttributeRenamer_5
    REPLACE_STR = adresse.
    CASE_DISP = YES
    ATTRCHOICE = All Attributes
    PATTERN_ACTION_DISP = REMOVEPREFIX
    MODE_CHOICE = RENAME
    -> AttributeManager_4
AttributeManager_4
    ATTR_TABLE:
      REMOVE xml_fragment
      REMOVE xml_id
      REMOVE xml_matched_element
      REMOVE xml_parent_child_pos
      REMOVE xml_parent_id
      RENAME_SET_VALUE qualitesPPM.qualitePPM.codeQualite > codeQualite
      RENAME_SET_VALUE bureauInstructeur.codeBureauInstructeur > codeBureauInstructeur
      RENAME_SET_VALUE bureauInstructeur.libelleBureauInstructeur > libelleBureauInstructeur
      REMOVE fme_feature_type
      REMOVE fme_rejection_code
      REMOVE _element_index
    -> BulkAttributeRenamer_6
BulkAttributeRenamer_6
    CASE_CHANGE_TYPE = lower
    ATTRCHOICE = All Attributes
    PATTERN_ACTION_DISP = CASECHANGE
    MODE_CHOICE = RENAME
    -> cvi.ppm (writer POSTGRES_3)
cvi.ppm (writer POSTGRES_3)
    attributes: prenom varchar(255), commune varchar(200), typevoielong varchar(200), codeppm varchar(200), datenaissance varchar(200), nompays varchar(200), email varchar(255), etatactivite varchar(200), coderegimefiscal varchar(200), typeppm varchar(200), libelleppm varchar(200), distributionspeciale varchar(200), typevoiecourt varchar(200), fax varchar(255), siren varchar(10), ligneachpostale varchar(200), nomvoie varchar(200), nom varchar(255), complementadresse varchar(200), codepostal varchar(200), repetition varchar(200), statutjuridique varchar(200), libelleoperateur varchar(200), numerovoie varchar(200), codepays varchar(200), codequalite varchar(200), telephone varchar(41), codebureauinstructeur varchar(200), formejuridique varchar(200), libellebureauinstructeur varchar(200)
dr (reader XML_4)
    attributes: campagne xml_char(10), codeEVV xml_char(11), codePPMBailleur xml_char(10), codeProduit xml_char(9), codeTypeDeclaration xml_char(4), libelleEVV xml_char(51), libelleProduit xml_char(81), libelleTypeDepot xml_char(7), libelleZoneViticole xml_char(4), mentionValorisante xml_char(133), motifNonRecolte xml_char(25), nomBailleur xml_char(51), qteAEliminer.volumeBailleur xml_decimal(7,3), qteAEliminer.volumeExploitant xml_decimal(8,3), qteAOPIGP.volumeBailleur xml_decimal(8,3), qteAOPIGP.volumeExploitant xml_decimal(9,3), qteAutreDestination.volumeBailleur xml_decimal(7,3), qteAutreDestination.volumeExploitant xml_decimal(8,3), qteConcentration.volumeBailleur xml_decimal(5,3), qteConcentration.volumeExploitant xml_decimal(7,3), qteEauEliminee.volumeBailleur xml_decimal(5,3), qteEauEliminee.volumeExploitant xml_decimal(7,3), qteMCNonUtilise.volumeBailleur xml_decimal(5,3), qteMCNonUtilise.volumeExploitant xml_decimal(7,3), qteRecolteCaveParticuliere.volumeBailleur xml_decimal(8,3), qteRecolteCaveParticuliere.volumeExploitant xml_decimal(9,3), qteRecolteTotale.volumeBailleur xml_decimal(8,3), qteRecolteTotale.volumeExploitant xml_decimal(10,3), qteSansAOPIGP.volumeBailleur xml_decimal(7,3), qteSansAOPIGP.volumeExploitant xml_decimal(9,3),
      qteVCI.volumeBailleur xml_decimal(6,3), qteVCI.volumeExploitant xml_decimal(8,3), qteVSI.volumeBailleur xml_decimal(6,3), qteVSI.volumeExploitant xml_decimal(7,3), qteVinification.volumeBailleur xml_decimal(8,3), qteVinification.volumeExploitant xml_decimal(9,3), qtesApporteesCave.qteApporteeCave.codeEVV xml_char(11), qtesApporteesCave.qteApporteeCave.libelleEVV xml_char(50), qtesApporteesCave.qteApporteeCave.volumeBailleur xml_decimal(7,3), qtesApporteesCave.qteApporteeCave.volumeExploitant xml_decimal(8,3), qtesApporteesCave.qteApporteeCave{}.codeEVV xml_char(11), qtesApporteesCave.qteApporteeCave{}.libelleEVV xml_char(50), qtesApporteesCave.qteApporteeCave{}.volumeBailleur xml_decimal(7,3), qtesApporteesCave.qteApporteeCave{}.volumeExploitant xml_decimal(9,3), qtesVenduesMouts.qteVendueMouts.codeEVV xml_char(11), qtesVenduesMouts.qteVendueMouts.libelleEVV xml_char(50), qtesVenduesMouts.qteVendueMouts.volumeBailleur xml_decimal(7,3), qtesVenduesMouts.qteVendueMouts.volumeExploitant xml_decimal(8,3), qtesVenduesMouts.qteVendueMouts{}.codeEVV xml_char(11), qtesVenduesMouts.qteVendueMouts{}.libelleEVV xml_char(50), qtesVenduesMouts.qteVendueMouts{}.volumeBailleur xml_decimal(7,3), qtesVenduesMouts.qteVendueMouts{}.volumeExploitant xml_decimal(8,3), qtesVenduesRaisins.qteVendueRaisins.codeEVV xml_char(11), qtesVenduesRaisins.qteVendueRaisins.libelleEVV xml_char(50), qtesVenduesRaisins.qteVendueRaisins.volumeBailleur xml_decimal(8,3), qtesVenduesRaisins.qteVendueRaisins.volumeExploitant xml_decimal(10,3), qtesVenduesRaisins.qteVendueRaisins{}.codeEVV xml_char(11), qtesVenduesRaisins.qteVendueRaisins{}.libelleEVV xml_char(50), qtesVenduesRaisins.qteVendueRaisins{}.volumeBailleur xml_decimal(7,3), qtesVenduesRaisins.qteVendueRaisins{}.volumeExploitant xml_decimal(9,3),
      superficie xml_decimal(9,4), xml_fragment xml_xml, xml_id xml_char(15), xml_matched_element xml_char(3), xml_parent_child_pos xml_char(1), xml_parent_id xml_char(1)
    -> ListExploder_6
ListExploder_6
    INDEX_ATTR = _element_index
    LIST_ATTR = qtesApporteesCave.qteApporteeCave{}
    ATTR_CONFLICT_RES = Use Incoming List
    ATTR_ACCUM_MODE = Merge Incoming List
    ELEMENTS -> ListExploder_7
    <REJECTED> -> ListExploder_7
ListExploder_7
    INDEX_ATTR = _element_index
    LIST_ATTR = qtesVenduesMouts.qteVendueMouts{}
    ATTR_CONFLICT_RES = Use Incoming List
    ATTR_ACCUM_MODE = Merge Incoming List
    ELEMENTS -> ListExploder_8
    <REJECTED> -> ListExploder_8
ListExploder_8
    INDEX_ATTR = _element_index
    LIST_ATTR = qtesVenduesRaisins.qteVendueRaisins{}
    ATTR_CONFLICT_RES = Use Incoming List
    ATTR_ACCUM_MODE = Merge Incoming List
    ELEMENTS -> AttributeManager_5
    <REJECTED> -> AttributeManager_5
AttributeManager_5
    ATTR_TABLE:
      REMOVE xml_fragment
      REMOVE xml_id
      REMOVE xml_matched_element
      REMOVE xml_parent_child_pos
      REMOVE xml_parent_id
      REMOVE fme_feature_type
      REMOVE fme_rejection_code
      REMOVE _element_index
    -> BulkAttributeRenamer_7
BulkAttributeRenamer_7
    CASE_CHANGE_TYPE = lower
    ATTRCHOICE = All Attributes
    PATTERN_ACTION_DISP = CASECHANGE
    MODE_CHOICE = RENAME
    -> cvi.recolte (writer POSTGRES_4)
cvi.recolte (writer POSTGRES_4)
    attributes: campagne varchar(10), codeevv varchar(11), codeppmbailleur varchar(10), codeproduit varchar(9), codetypedeclaration varchar(4), libelleevv varchar(51), libelleproduit varchar(81), libelletypedepot varchar(7), libellezoneviticole varchar(4), mentionvalorisante varchar(133), motifnonrecolte varchar(25), nombailleur varchar(51), qteaeliminer_volumebailleur varchar(200), qteaeliminer_volumeexploitant varchar(200), qteaopigp_volumebailleur varchar(200), qteaopigp_volumeexploitant varchar(200), qteautredestination_volumebailleur varchar(200), qteautredestination_volumeexploitant varchar(200), qteconcentration_volumebailleur varchar(200), qteconcentration_volumeexploitant varchar(200), qteeaueliminee_volumebailleur varchar(200), qteeaueliminee_volumeexploitant varchar(200), qtemcnonutilise_volumebailleur varchar(200), qtemcnonutilise_volumeexploitant varchar(200), qterecoltecaveparticuliere_volumebailleur varchar(200), qterecoltecaveparticuliere_volumeexploitant varchar(200), qterecoltetotale_volumebailleur varchar(200), qterecoltetotale_volumeexploitant varchar(200), qtesansaopigp_volumebailleur varchar(200), qtesansaopigp_volumeexploitant varchar(200),
      qtevci_volumebailleur varchar(200), qtevci_volumeexploitant varchar(200), qtevsi_volumebailleur varchar(200), qtevsi_volumeexploitant varchar(200), qtevinification_volumebailleur varchar(200), qtevinification_volumeexploitant varchar(200), qtesapporteescave_qteapporteecave_codeevv varchar(200), qtesapporteescave_qteapporteecave_libelleevv varchar(200), qtesapporteescave_qteapporteecave_volumebailleur varchar(200), qtesapporteescave_qteapporteecave_volumeexploitant varchar(200), volumebailleur varchar(200), volumeexploitant varchar(200), qtesvenduesmouts_qtevenduemouts_codeevv varchar(200), qtesvenduesmouts_qtevenduemouts_libelleevv varchar(200), qtesvenduesmouts_qtevenduemouts_volumebailleur varchar(200), qtesvenduesmouts_qtevenduemouts_volumeexploitant varchar(200), qtesvenduesraisins_qtevendueraisins_codeevv varchar(200), qtesvenduesraisins_qtevendueraisins_libelleevv varchar(200), qtesvenduesraisins_qtevendueraisins_volumebailleur varchar(200), qtesvenduesraisins_qtevendueraisins_volumeexploitant varchar(200), superficie numeric(9,4)
Note: FONCIER
PCV (reader XML_1)
    attributes: SPCVs.SPCV.campagnePlantation xml_char(10), SPCVs.SPCV.codeAire xml_decimal(4,0), SPCVs.SPCV.codeCepage xml_decimal(5,0), SPCVs.SPCV.codeCouleurCepage xml_char(3), SPCVs.SPCV.codeEVV xml_char(11), SPCVs.SPCV.codePorteGreffe xml_char(5), SPCVs.SPCV.codeProduit xml_char(9), SPCVs.SPCV.dateDebutGestion xml_char(11), SPCVs.SPCV.dateFinGestion xml_char(11), SPCVs.SPCV.dateModeFaireValoir xml_char(11), SPCVs.SPCV.dateModificationFonciere xml_char(11), SPCVs.SPCV.ecartPied xml_decimal(4,0), SPCVs.SPCV.ecartRang xml_decimal(4,0), SPCVs.SPCV.etatMetier xml_char(9), SPCVs.SPCV.libelleAire xml_char(59), SPCVs.SPCV.libelleCepage xml_char(33), SPCVs.SPCV.libelleEVV xml_char(51), SPCVs.SPCV.libelleModeFaireValoir xml_char(46), SPCVs.SPCV.libelleMotifEncepagement xml_char(255), SPCVs.SPCV.libellePorteGreffe xml_char(33), SPCVs.SPCV.libelleProduit xml_char(31), SPCVs.SPCV.numeroOrdre xml_decimal(3,0), SPCVs.SPCV.segment xml_decimal(2,0), SPCVs.SPCV.superficie xml_decimal(7,4), SPCVs.SPCV{}.campagnePlantation xml_char(10), SPCVs.SPCV{}.codeAire xml_decimal(4,0), SPCVs.SPCV{}.codeCepage xml_decimal(5,0), SPCVs.SPCV{}.codeCouleurCepage xml_char(3), SPCVs.SPCV{}.codeEVV xml_char(11), SPCVs.SPCV{}.codePorteGreffe xml_char(5),
      SPCVs.SPCV{}.codeProduit xml_char(9), SPCVs.SPCV{}.dateDebutGestion xml_char(11), SPCVs.SPCV{}.dateFinGestion xml_char(11), SPCVs.SPCV{}.dateModeFaireValoir xml_char(11), SPCVs.SPCV{}.dateModificationFonciere xml_char(11), SPCVs.SPCV{}.ecartPied xml_decimal(4,0), SPCVs.SPCV{}.ecartRang xml_decimal(4,0), SPCVs.SPCV{}.etatMetier xml_char(9), SPCVs.SPCV{}.libelleAire xml_char(255), SPCVs.SPCV{}.libelleCepage xml_char(33), SPCVs.SPCV{}.libelleEVV xml_char(51), SPCVs.SPCV{}.libelleModeFaireValoir xml_char(46), SPCVs.SPCV{}.libelleMotifEncepagement xml_char(255), SPCVs.SPCV{}.libellePorteGreffe xml_char(33), SPCVs.SPCV{}.libelleProduit xml_char(31), SPCVs.SPCV{}.numeroOrdre xml_char(255), SPCVs.SPCV{}.segment xml_decimal(2,0), SPCVs.SPCV{}.superficie xml_decimal(7,4), civiliteProprietaire xml_char(4), codeCommune xml_decimal(4,0), codeDepartement xml_char(3), codeINSEECommune xml_char(7), contenanceCadastrale xml_char(255), dateDebutValidite xml_char(11), libelleCommune xml_char(255), lieuDit xml_char(255), nomProprietaire xml_char(255), prenomProprietaire xml_char(255), referenceCadastrale xml_char(255), xml_fragment xml_xml,
      xml_id xml_char(16), xml_matched_element xml_char(4), xml_parent_child_pos xml_char(1), xml_parent_id xml_char(1)
    -> ListExploder
ListExploder
    INDEX_ATTR = _element_index
    LIST_ATTR = SPCVs.SPCV{}
    ATTR_CONFLICT_RES = Use Incoming List
    ATTR_ACCUM_MODE = Merge Incoming List
    ELEMENTS -> AttributeManager
    <REJECTED> -> AttributeManager_2
AttributeManager
    ATTR_TABLE:
      REMOVE SPCVs.SPCV.campagnePlantation
      REMOVE SPCVs.SPCV.codeAire
      REMOVE SPCVs.SPCV.codeCepage
      REMOVE SPCVs.SPCV.codeCouleurCepage
      REMOVE SPCVs.SPCV.codeEVV
      REMOVE SPCVs.SPCV.codePorteGreffe
      REMOVE SPCVs.SPCV.codeProduit
      REMOVE SPCVs.SPCV.dateDebutGestion
      REMOVE SPCVs.SPCV.dateFinGestion
      REMOVE SPCVs.SPCV.dateModeFaireValoir
      REMOVE SPCVs.SPCV.dateModificationFonciere
      REMOVE SPCVs.SPCV.ecartPied
      REMOVE SPCVs.SPCV.ecartRang
      REMOVE SPCVs.SPCV.etatMetier
      REMOVE SPCVs.SPCV.libelleAire
      REMOVE SPCVs.SPCV.libelleCepage
      REMOVE SPCVs.SPCV.libelleEVV
      REMOVE SPCVs.SPCV.libelleModeFaireValoir
      REMOVE SPCVs.SPCV.libelleMotifEncepagement
      REMOVE SPCVs.SPCV.libellePorteGreffe
      REMOVE SPCVs.SPCV.libelleProduit
      REMOVE SPCVs.SPCV.numeroOrdre
      REMOVE SPCVs.SPCV.segment
      REMOVE SPCVs.SPCV.superficie
      REMOVE xml_fragment
      REMOVE xml_id
      REMOVE xml_matched_element
      REMOVE xml_parent_child_pos
      REMOVE xml_parent_id
      REMOVE fme_feature_type
      REMOVE _element_index
    -> BulkAttributeRenamer
BulkAttributeRenamer
    REPLACE_STR = SPCVs.SPCV.
    CASE_DISP = YES
    ATTRCHOICE = All Attributes
    PATTERN_ACTION_DISP = REMOVEPREFIX
    MODE_CHOICE = RENAME
    -> cvi.foncier (writer POSTGRES_1)
AttributeManager_2
    ATTR_TABLE:
      REMOVE campagnePlantation
      REMOVE codeAire
      REMOVE codeCepage
      REMOVE codeCouleurCepage
      REMOVE codeEVV
      REMOVE codePorteGreffe
      REMOVE codeProduit
      REMOVE dateDebutGestion
      REMOVE dateFinGestion
      REMOVE dateModeFaireValoir
      REMOVE dateModificationFonciere
      REMOVE ecartPied
      REMOVE ecartRang
      REMOVE etatMetier
      REMOVE libelleAire
      REMOVE libelleCepage
      REMOVE libelleEVV
      REMOVE libelleModeFaireValoir
      REMOVE libelleMotifEncepagement
      REMOVE libellePorteGreffe
      REMOVE libelleProduit
      REMOVE numeroOrdre
      REMOVE segment
      REMOVE superficie
      REMOVE xml_fragment
      REMOVE xml_id
      REMOVE xml_matched_element
      REMOVE xml_parent_child_pos
      REMOVE xml_parent_id
      REMOVE fme_feature_type
      REMOVE fme_rejection_code
    -> BulkAttributeRenamer_2
BulkAttributeRenamer_2
    REPLACE_STR = SPCVs.SPCV.
    CASE_DISP = YES
    ATTRCHOICE = All Attributes
    PATTERN_ACTION_DISP = REMOVEPREFIX
    MODE_CHOICE = RENAME
    -> cvi.foncier (writer POSTGRES_1)
cvi.foncier (writer POSTGRES_1)
    attributes: civiliteproprietaire varchar(4), nomproprietaire varchar(255), prenomproprietaire varchar(255), referencecadastrale varchar(255), codecommune int2, codedepartement varchar(3), codeinseecommune varchar(7), contenancecadastrale varchar(255), datedebutvalidite varchar(11), libellecommune varchar(255), lieudit varchar(255), campagneplantation varchar(200), codeaire varchar(200), codecepage varchar(200), codecouleurcepage varchar(200), codeevv varchar(200), codeportegreffe varchar(200), codeproduit varchar(200), datedebutgestion varchar(200), datefingestion varchar(200), datemodefairevaloir varchar(200), datemodificationfonciere varchar(200), ecartpied varchar(200), ecartrang varchar(200), etatmetier varchar(200), libelleaire varchar(200), libellecepage varchar(200), libelleevv varchar(200), libellemodefairevaloir varchar(200), libellemotifencepagement varchar(200),
      libelleportegreffe varchar(200), libelleproduit varchar(200), numeroordre varchar(200), segment varchar(200), superficie varchar(200)

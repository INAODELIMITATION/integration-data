FME workspace download-edigeo.fmw

Parameters:
- date_version = latest   # date de version
- sortie = C:\Users\baussier\Desktop\edigeo
- type = parcelles   # type 

SQLCreator
    DATASET = srv_sig
    EXPOSED_ATTRIBUTE_LIST = code_dept
    FORMAT = POSTGRES
    POSTGRES_CREATE_FEATURE_TABLES_FROM_DATA = Yes
    POSTGRES_NAMED_CONNECTION = srv_sig
    POSTGRES_QUERY_FEATURE_TYPES_FOR_MERGE_FILTERS = Yes
    POSTGRES_READ_TIME_WITH_TIMEZONE = Yes
    POSTGRES_SCHEMAS_FOR_TABLE_LISTING = cvi edigeo etalab ign_bd_cadastre ign_bd_carto ign_bd_topo mae metier_inao work
    SQL_STATEMENT:
      select distinct code_dept from "ign_bd_carto"."departement"
      order by code_dept
    RESULT -> AttributeCreator
AttributeCreator
    ATTR_TABLE:
      SET_TO departement = @Value(code_dept)
      SET_TO date = $(date_version)
      SET_TO repertoire_sortie = $(sortie)
      SET_TO type = $(type)
    -> HTTPCaller
HTTPCaller
    CONNECTION_TIMEOUT_LENGTH = 60
    ERROR_ATTR = _error
    FILE_PATH_ATTR = _response_file_path
    FOLLOW_REDIRECTS = Yes
    HTTP_METHOD = GET
    OUTPUT_FILENAME = @Value(repertoire_sortie)\@Value(code_dept)_@Value(type).json.gz
    RESPONSE_HEADER_LIST_ATTR = _headers
    SAVE_FILE = File
    SAVE_MULTI = No
    STATUS_CODE_ATTR = _http_status_code
    TARGET_URL = https://cadastre.data.gouv.fr/data/etalab-cadastre/@Value(date)/geojson/departements/@Value(code_dept)/cadastre-@Value(code_dept)-@Value(type).json.gz
    TRANSFER_TIMEOUT_LENGTH = 90
    USE_COOKIES = No
    VERIFY_SSL_CERTIFICATES = Yes

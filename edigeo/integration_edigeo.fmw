FME workspace integration_edigeo.fmw

Parameters:
- SourceDataset_GEOJSON = ""$(FME_MF_DIR)traitement\1\22_batiments.json" "$(FME_MF_DIR)traitement\1\22_communes.json" "$(FME_MF_DIR)traitement\1\22_feuilles.json" "$(FME_MF_DIR)traitement\1\22_lieux_dits.json" "$(FME_MF_DIR)traitement\1\22_parcelles.json" "$(FME_MF_DIR)traitement\1\22_sections.json" "$(FME_MF_DIR)traitement\1\23_batiments.json" "$(FME_MF_DIR)traitement\1\23_communes.json" "$(FME_MF_DIR)traitement\1\23_feuilles.json" "$(FME_MF_DIR)traitement\1\23_lieux_dits.json" "$(FME_MF_DIR)traitement\1\23_parcelles.json" "$(FME_MF_DIR)traitement\1\23_sections.json" "$(FME_MF_DIR)traitement\1\24_batiments.json" "$(FME_MF_DIR)traitement\1\24_communes.json" "$(FME_MF_DIR)traitement\1\24_feuilles.json" "$(FME_MF_DIR)traitement\1\24_lieux_dits.json" "$(FME_MF_DIR)traitement\1\24_parcelles.json" "$(FME_MF_DIR)traitement\1\24_sections.json" "$(FME_MF_DIR)traitement\1\25_batiments.json" "$(FME_MF_DIR)traitement\1\25_communes.json" "$(FME_MF_DIR)traitement\1\25_feuilles.json" "$(FME_MF_DIR)traitement\1\25_lieux_dits.json" "$(FME_MF_DIR)traitement\1\25_parcelles.json" "$(FME_MF_DIR)traitement\1\25_sections.json" "$(FME_MF_DIR)traitement\1\26_batiments.json" "$(FME_MF_DIR)traitement\1\26_communes.json" "$(FME_MF_DIR)traitement\1\26_feuilles.json" "$(FME_MF_DIR)traitement\1\26_lieux_dits.json" "$(FME_MF_DIR)traitement\1\26_parcelles.json" "$(FME_MF_DIR)traitement\1\26_sections.json" "$(FME_MF_DIR)traitement\1\27_batiments.json" "$(FME_MF_DIR)traitement\1\27_communes.json" "$(FME_MF_DIR)traitement\1\27_feuilles.json" "$(FME_MF_DIR)traitement\1\27_lieux_dits.json" "$(FME_MF_DIR)traitement\1\27_parcelles.json" "$(FME_MF_DIR)traitement\1\27_sections.json" "$(FME_MF_DIR)traitement\1\28_batiments.json" "$(FME_MF_DIR)traitement\1\28_communes.json" "$(FME_MF_DIR)traitement\1\28_feuilles.json" "$(FME_MF_DIR)traitement\1\28_lieux_dits.json" "$(FME_MF_DIR)traitement\1\28_parcelles.json" "$(FME_MF_DIR)traitement\1\28_sections.json" "$(FME_MF_DIR)traitement\1\29_batiments.json" "$(FME_MF_DIR)traitement\1\29_communes.json" "$(FME_MF_DIR)traitement\1\29_feuilles.json" "$(FME_MF_DIR)traitement\1\29_lieux_dits.json" "$(FME_MF_DIR)traitement\1\29_parcelles.json" "$(FME_MF_DIR)traitement\1\29_sections.json" "$(FME_MF_DIR)traitement\1\30_batiments.json" "$(FME_MF_DIR)traitement\1\30_communes.json" "$(FME_MF_DIR)traitement\1\30_feuilles.json" "$(FME_MF_DIR)traitement\1\30_lieux_dits.json" "$(FME_MF_DIR)traitement\1\30_parcelles.json" "$(FME_MF_DIR)traitement\1\30_sections.json""   # Source GeoJSON File or URL

Readers:
- GEOJSON_1: GEOJSON from $(SourceDataset_GEOJSON)

Writers:
- POSTGIS_1: POSTGIS to local
- POSTGIS_2: POSTGIS to local
- POSTGIS_3: POSTGIS to local
- POSTGIS_4: POSTGIS to local
- POSTGIS_5: POSTGIS to local

51_batiments (reader GEOJSON_1)
    attributes: type string, nom string, commune string, created string, updated string, echelle int, contenance float, section string, id string, numero string, qualite string, code string, modeConfection string, prefixe string
    -> FilenamePartExtractor
FilenamePartExtractor
    EXTENSION_ATTR = _extension
    SRC_ATTR = @Value(fme_dataset)
    ROOTNAME_ATTR = _rootname
    DIRNAME_ATTR = _dirname
    FULLNAME_ATTR = _filename
    DIRPATH_ATTR = _dirpath
    -> TestFilter
TestFilter
    DEFAULT_VALUE = <UNFILTERED>
    TEST_LIST = BOOL_OP,OR,COMPOSITE_TEST,<Unused>,TEST_CLAUSE,"TEST @Value(_rootname) CONTAINS_REGEX bati",bati,BOOL_OP,OR,COMPOSITE_TEST,<Unused>,TEST_CLAUSE,"TEST @Value(_rootname) CONTAINS_REGEX parcelle",parcelle,BOOL_OP,OR,COMPOSITE_TEST,<Unused>,TEST_CLAUSE,"TEST @Value(_rootname) CONTAINS_REGEX feuille",section,BOOL_OP,OR,COMPOSITE_TEST,<Unused>,TEST_CLAUSE,"TEST @Value(_rootname) CONTAINS_REGEX lieu",lieu,BOOL_OP,OR,COMPOSITE_TEST,<Unused>,TEST_CLAUSE,"TEST @Value(_rootname) CONTAINS_REGEX commune",commune
    bati -> data.batiment (writer POSTGIS_1)
    parcelle -> data.parcelle (writer POSTGIS_2)
    section -> data.section (writer POSTGIS_4)
    lieu -> data.lieu_dit (writer POSTGIS_5)
    commune -> data.commune (writer POSTGIS_3)
data.batiment (writer POSTGIS_1)
    attributes: type text, nom text, commune text, created text, updated text
data.parcelle (writer POSTGIS_2)
    attributes: id text, commune text, prefixe text, section text, numero text, contenance int8, created text, updated text
data.section (writer POSTGIS_4)
    attributes: id text, commune text, prefixe text, section text, numero text, qualite text, modeConfection text, echelle int8, created text, updated text
data.lieu_dit (writer POSTGIS_5)
    attributes: nom text, commune text, created text, updated text
data.commune (writer POSTGIS_3)
    attributes: id text, nom text, created text, updated text

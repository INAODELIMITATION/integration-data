FME workspace recuperation_edimap.fmw

Parameters:
- SourceDataset_PATH_3 = C:\Users\baussier\Desktop\cremant_bourgogne\0_src_datas_sig\**\/   # Source Folder and File Pathnames Folder
- FEATURE_TYPES_2 =
- DestDataset_POSTGIS = local   # Connection

Readers:
- PATH_1: PATH from $(SourceDataset_PATH_3)

Writers:
- POSTGIS_1: POSTGIS to $(DestDataset_POSTGIS)

PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> StringSearcher
TestFilter
    DEFAULT_VALUE = <UNFILTERED>
    TEST_LIST = "BOOL_OP,OR,COMPOSITE_TEST,""""""<Unused>"""""",TEST_CLAUSE,CASE_INSENSITIVE_TEST @Value(path_rootname) CONTAINS_REGEX commune",commune,"BOOL_OP,OR,COMPOSITE_TEST,""""""<Unused>"""""",TEST_CLAUSE,CASE_INSENSITIVE_TEST @Value(path_rootname) CONTAINS_REGEX sub.*section",section,"BOOL_OP,OR,COMPOSITE_TEST,""""""<Unused>"""""",TEST_CLAUSE,CASE_INSENSITIVE_TEST @Value(path_rootname) CONTAINS_REGEX lieu",lieu,"BOOL_OP,OR,COMPOSITE_TEST,""""""<Unused>"""""",TEST_CLAUSE,CASE_INSENSITIVE_TEST @Value(path_filename) CONTAINS_REGEX parc\.tab",parcelle,"BOOL_OP,OR,COMPOSITE_TEST,""""""<Unused>"""""",TEST_CLAUSE,CASE_INSENSITIVE_TEST @Value(path_rootname) CONTAINS_REGEX bati",bati
    commune -> AttributeCreator
    section -> AttributeCreator_2
    lieu -> AttributeCreator_3
    parcelle -> AttributeCreator_4
    bati -> AttributeCreator_5
AttributeCreator [off]
    ATTR_TABLE = SET_TO type = commune
    -> FeatureReader [INITIATOR] [off]
FeatureReader [off]
    ATTRS_TO_EXPOSE = GB_IDENT IDU
    ATTR_ACCUM_MODE = Merge Initiator and Result
    ATTR_CONFLICT_RES = Use Result
    COMBINE_GEOM = Use Result
    DATASET = @Value(path_windows)
    FORMAT = MITAB
    INTERACT = <No Spatial Filter>
    MITAB_USE_SEARCH_ENVELOPE = NO
    MITAB__MITAB_FULL_ENHANCED_GEOMETRY = YES
    OUTPUT_FEATURES_DISPLAY = Schema and Data Features
    <OTHER> -> AttributeManager [off]
AttributeManager [off]
    ATTR_TABLE:
      SET_TO idu = @Value(part)@Value(IDU)
      RENAME_SET_VALUE GB_IDENT > nom
      REMOVE IDU
      REMOVE part
      REMOVE path_unix
      REMOVE path_rootname
      REMOVE path_filename
      REMOVE path_extension
      REMOVE path_filesize
      REMOVE path_ownername
      REMOVE path_readonly
      REMOVE path_modified_date
      REMOVE path_created_date
      REMOVE path_accessed_date
      REMOVE path_directory_unix
      REMOVE path_directory_windows
      REMOVE path_type
      REMOVE fme_feature_type
      REMOVE _first_match
      REMOVE sub_exp{}.part
      REMOVE sub_exp{}.startIndex
      REMOVE startIndex
    -> Junction
AttributeCreator_2 [off]
    ATTR_TABLE = SET_TO type = section
    -> FeatureReader_2 [INITIATOR] [off]
FeatureReader_2 [off]
    ATTRS_TO_EXPOSE = GB_IDENT IDU
    ATTR_ACCUM_MODE = Merge Initiator and Result
    ATTR_CONFLICT_RES = Use Result
    COMBINE_GEOM = Use Result
    DATASET = @Value(path_windows)
    FORMAT = MITAB
    INTERACT = <No Spatial Filter>
    MITAB_USE_SEARCH_ENVELOPE = NO
    MITAB__MITAB_FULL_ENHANCED_GEOMETRY = YES
    OUTPUT_FEATURES_DISPLAY = Schema and Data Features
    <OTHER> -> AttributeManager_2 [off]
AttributeManager_2 [off]
    ATTR_TABLE:
      REMOVE GB_IDENT
      RENAME_SET_VALUE IDU > idu
      REMOVE part
      REMOVE path_unix
      REMOVE path_rootname
      REMOVE path_filename
      REMOVE path_extension
      REMOVE path_filesize
      REMOVE path_ownername
      REMOVE path_readonly
      REMOVE path_modified_date
      REMOVE path_created_date
      REMOVE path_accessed_date
      REMOVE path_directory_unix
      REMOVE path_directory_windows
      REMOVE path_type
      REMOVE fme_feature_type
      REMOVE _first_match
      REMOVE sub_exp{}.part
      REMOVE sub_exp{}.startIndex
      REMOVE startIndex
    -> Junction
AttributeCreator_3 [off]
    ATTR_TABLE = SET_TO type = lieu
    -> FeatureReader_3 [INITIATOR] [off]
FeatureReader_3 [off]
    ATTRS_TO_EXPOSE = GB_IDENT IDU
    ATTR_ACCUM_MODE = Merge Initiator and Result
    ATTR_CONFLICT_RES = Use Result
    COMBINE_GEOM = Use Result
    DATASET = @Value(path_windows)
    FORMAT = MITAB
    INTERACT = <No Spatial Filter>
    MITAB_USE_SEARCH_ENVELOPE = NO
    MITAB__MITAB_FULL_ENHANCED_GEOMETRY = YES
    OUTPUT_FEATURES_DISPLAY = Schema and Data Features
    <OTHER> -> AttributeManager_3 [off]
AttributeManager_3 [off]
    ATTR_TABLE:
      RENAME_SET_VALUE GB_IDENT > nom
      REMOVE IDU
      REMOVE part
      REMOVE path_unix
      REMOVE path_rootname
      REMOVE path_filename
      REMOVE path_extension
      REMOVE path_filesize
      REMOVE path_ownername
      REMOVE path_readonly
      REMOVE path_modified_date
      REMOVE path_created_date
      REMOVE path_accessed_date
      REMOVE path_directory_unix
      REMOVE path_directory_windows
      REMOVE path_type
      REMOVE fme_feature_type
      REMOVE _first_match
      REMOVE sub_exp{}.part
      REMOVE sub_exp{}.startIndex
      REMOVE startIndex
    -> Junction
AttributeCreator_4
    ATTR_TABLE = SET_TO type = parcelle
    -> FeatureReader_4 [INITIATOR]
FeatureReader_4
    ATTRS_TO_EXPOSE = GB_IDENT IDU
    ATTR_ACCUM_MODE = Merge Initiator and Result
    ATTR_CONFLICT_RES = Use Result
    COMBINE_GEOM = Use Result
    DATASET = @Value(path_windows)
    FORMAT = MITAB
    INTERACT = <No Spatial Filter>
    MITAB_USE_SEARCH_ENVELOPE = NO
    MITAB__MITAB_FULL_ENHANCED_GEOMETRY = YES
    OUTPUT_FEATURES_DISPLAY = Schema and Data Features
    <OTHER> -> AttributeManager_4
AttributeManager_4
    ATTR_TABLE:
      REMOVE GB_IDENT
      RENAME_SET_VALUE IDU > idu
      REMOVE part
      REMOVE path_unix
      REMOVE path_rootname
      REMOVE path_filename
      REMOVE path_extension
      REMOVE path_filesize
      REMOVE path_ownername
      REMOVE path_readonly
      REMOVE path_modified_date
      REMOVE path_created_date
      REMOVE path_accessed_date
      REMOVE path_directory_unix
      REMOVE path_directory_windows
      REMOVE path_type
      REMOVE fme_feature_type
      REMOVE _first_match
      REMOVE sub_exp{}.part
      REMOVE sub_exp{}.startIndex
      REMOVE startIndex
    -> Junction
AttributeCreator_5 [off]
    ATTR_TABLE = SET_TO type = bati
    -> FeatureReader_5 [INITIATOR] [off]
FeatureReader_5 [off]
    ATTRS_TO_EXPOSE = GB_IDENT IDU
    ATTR_ACCUM_MODE = Merge Initiator and Result
    ATTR_CONFLICT_RES = Use Result
    COMBINE_GEOM = Use Result
    DATASET = @Value(path_windows)
    FORMAT = MITAB
    INTERACT = <No Spatial Filter>
    MITAB_USE_SEARCH_ENVELOPE = NO
    MITAB__MITAB_FULL_ENHANCED_GEOMETRY = YES
    OUTPUT_FEATURES_DISPLAY = Schema and Data Features
    <OTHER> -> AttributeManager_5 [off]
AttributeManager_5 [off]
    ATTR_TABLE:
      REMOVE GB_IDENT
      REMOVE IDU
      REMOVE part
      REMOVE path_unix
      REMOVE path_rootname
      REMOVE path_filename
      REMOVE path_extension
      REMOVE path_filesize
      REMOVE path_ownername
      REMOVE path_readonly
      REMOVE path_modified_date
      REMOVE path_created_date
      REMOVE path_accessed_date
      REMOVE path_directory_unix
      REMOVE path_directory_windows
      REMOVE path_type
      REMOVE fme_feature_type
      REMOVE _first_match
      REMOVE sub_exp{}.part
      REMOVE sub_exp{}.startIndex
      REMOVE startIndex
    -> Junction
Junction
    -> int_cremant_bourgogne (writer POSTGIS_1)
int_cremant_bourgogne (writer POSTGIS_1)
    attributes: type text, path_windows text, idu text, nom text

Bookmark: RECHERCHE DU NUM DEPARTEMENT DANS NOM DU DOSSIER
StringSearcher
    CASE = no
    MATCHED_PARTS_ATTR = sub_exp
    MATCHED_RESULT_ATTR = _first_match
    REGEXP = (?:\\)(\d{2})(?:_.+\\)
    STRING_TO_SEARCH = @Value(path_windows)
    MATCHED -> ListIndexer
ListIndexer
    INDEX = 0
    LIST_ATTR = sub_exp{}
    -> TestFilter

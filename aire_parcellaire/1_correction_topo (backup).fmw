FME workspace 1_correction_topo (backup).fmw

Parameters:
- SourceDataset_MITAB = C:\Users\baussier\Desktop\vecteur pour integration bdd\non traite\**\*.tab   # Source MapInfo TAB File(s)
- SourceDataset_ESRISHAPE = C:\Users\baussier\Desktop\vecteur pour integration bdd\non traite\**\*.shp   # Source Esri Shapefile(s)
- FEATURE_TYPES =

Readers:
- MITAB_1: MITAB from $(SourceDataset_MITAB)
- ESRISHAPE_1: ESRISHAPE from $(SourceDataset_ESRISHAPE)

Writers:
- POSTGIS_1: POSTGIS to srv_sig_1

07324_CDR-df_2019_Carte (reader MITAB_1)
    attributes: INSEE char(9), COMMUNE char(100), NOM_AOC char(254), COULEUR_AOC char(10), CODE_CVI char(10), REF_APPROBATION_INAO char(80), SURF_DGFiP_HA decimal(10,4), URL_FICHE char(254), LIEUDIT char(80), SUP_CALCULEE float, INDP char(80), CODM char(80), DEPT integer, PARTIE char(1), AOC char(80), TEX2 char(80), SUPF float, IDU char(20), GB_IDNUM integer, COAR char(1), TEX char(80), SECTION char(2), GB_IDENT char(40), Sup_tot_calculee float
    -> Junction
correctif4_topoo (reader ESRISHAPE_1)
    attributes: id long, id_uni char(254), appellatio char(254), insee char(5), nomcom char(254), insee2018 char(5), nom2018 char(254), erreur_tam char(20), erreur_t_1 char(20), erreur_t_2 char(9), erreur_t_3 char(100), erreur_t_4 char(254), _uid_ number(20,0), id_zone long, id_aire long, lbl_aire char(254), id_app long
    -> Junction
Junction
    -> AttributeManager
AttributeManager
    ATTR_TABLE:
      RENAME_SET_VALUE INSEE > insee
      RENAME_SET_VALUE COMMUNE > nom_com
      REMOVE NOM_AOC
      REMOVE COULEUR_AOC
      REMOVE CODE_CVI
      REMOVE REF_APPROBATION_INAO
      REMOVE SURF_DGFiP_HA
      REMOVE URL_FICHE
      REMOVE LIEUDIT
      REMOVE SUP_CALCULEE
      REMOVE INDP
      REMOVE CODM
      REMOVE DEPT
      REMOVE PARTIE
      REMOVE AOC
      REMOVE TEX2
      REMOVE SUPF
      REMOVE IDU
      REMOVE GB_IDNUM
      REMOVE COAR
      REMOVE TEX
      REMOVE SECTION
      REMOVE GB_IDENT
      REMOVE Sup_tot_calculee
      RENAME_SET_VALUE fme_dataset > dataset
      REMOVE fme_feature_type
      REMOVE id
      REMOVE appellatio
      RENAME_SET_VALUE nomcom > nom_com
      REMOVE insee2018
      REMOVE nom2018
      REMOVE erreur_tam
      REMOVE erreur_t_1
      REMOVE erreur_t_2
      REMOVE erreur_t_3
      REMOVE erreur_t_4
      REMOVE _uid_
      REMOVE id_zone
      REMOVE id_aire
      REMOVE lbl_aire
      REMOVE id_app
      SET_TO dataset = @Value(dataset)@Value(id_uni)
    -> FeatureWriter [Result]
FeatureWriter
    COORDSYS = EPSG:2154
    DATASET = srv_sig_1
    DATASET_ATTR = _dataset
    FEATURE_TYPE_LIST_ATTR = _feature_type
    FORMAT = POSTGIS
    POSTGIS_BULK_COPY = YES
    POSTGIS_COORDINATE_SYSTEM_GRANULARITY = FEATURE_TYPE
    POSTGIS_GENERIC_GEOMETRY = no
    POSTGIS_INSERT_TEXT_GEOMETRY = NO
    POSTGIS_LOWERCASE_ATTRIBUTE_NAMES = No
    POSTGIS_NAMED_CONNECTION = srv_sig_1
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> SQLExecutor [INITIATOR]
SQLExecutor
    COMBINE_ATTRS = Result Attributes Only
    COMBINE_GEOM = Result Geometry Only
    DATASET = srv_sig_1
    FORMAT = POSTGIS
    POSTGIS_DISABLE_COLLECTION_SPLITTING = yes
    POSTGIS_NAMED_CONNECTION = srv_sig_1
    POSTGIS_QUERY_FEATURE_TYPES_FOR_MERGE_FILTERS = Yes
    POSTGIS_READ_TIME_WITH_TIMEZONE = Yes
    POSTGIS_SCHEMAS_FOR_TABLE_LISTING = metier_inao work public
    POSTGIS_USE_TRUE_POSTGIS_TYPES = yes
    SQL_STATEMENT:
      DROP TABLE IF EXISTS work.live_result;

      CREATE TABLE work.live_result(
          id serial primary key,
          insee text,
          loc_insee text,
          id_aire integer,
          lbl_aire text,
          dataset text,
          geom geometry(multipolygon,2154));

      CREATE INDEX ON work.live_result USING GIST(geom);

      INSERT INTO work.live_result (insee, dataset, geom)
      SELECT
          insee,
          dataset,
          ST_MULTI(ST_COLLECTIONEXTRACT(ST_MAKEVALID(ST_UNION(geom)),3)) geom
      FROM
      	(SELECT
              insee,
              dataset,
              ST_MAKEVALID(ST_SNAPTOGRID((ST_DUMP(geom)).geom,0.01)) geom
      	FROM work.live) req1
      GROUP BY insee, dataset;

      DROP TABLE IF EXISTS work.live;

      UPDATE work.live_result lr
      SET loc_insee = c.id
      FROM edigeo.commune  c
      WHERE ST_intersects(st_pointonsurface(lr.geom),c.geom);
    INITIATOR -> FeatureReader [INITIATOR]
FeatureReader
    ATTRIBUTES = work.live_result,"id,insee,dataset"
    ATTR_ACCUM_MODE = Only Use Result
    COMBINE_GEOM = Use Result
    COORDSYS = EPSG:2154
    DATASET = srv_sig_1
    FEATURETYPES = work.live_result
    FORMAT = POSTGIS
    INTERACT = <No Spatial Filter>
    OUTPUT_FEATURES_DISPLAY = Data Features
    POSTGIS_DISABLE_COLLECTION_SPLITTING = yes
    POSTGIS_FEATURES_PER_FETCH = 10000
    POSTGIS_NAMED_CONNECTION = srv_sig_1
    POSTGIS_QUERY_FEATURE_TYPES_FOR_MERGE_FILTERS = Yes
    POSTGIS_READ_TIME_WITH_TIMEZONE = Yes
    POSTGIS_SCHEMAS_FOR_TABLE_LISTING = metier_inao work public
    POSTGIS_USE_SEARCH_ENVELOPE = NO
    POSTGIS_USE_TRUE_POSTGIS_TYPES = yes
    work.live_result -> SQLExecutor_Result
SQLExecutor_Result: Inspector

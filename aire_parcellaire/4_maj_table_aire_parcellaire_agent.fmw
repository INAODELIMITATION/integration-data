FME workspace 4_maj_table_aire_parcellaire_agent.fmw

SQLCreator
    DATASET = srv_sig
    EXPOSED_ATTRIBUTE_LIST = appellation,crinao,denomination,id,id_app,id_denom,new_insee,new_nomcom,old_insee,old_nomcom,type_ig
    FORMAT = POSTGRES
    POSTGRES_CREATE_FEATURE_TABLES_FROM_DATA = Yes
    POSTGRES_NAMED_CONNECTION = srv_sig
    POSTGRES_QUERY_FEATURE_TYPES_FOR_MERGE_FILTERS = Yes
    POSTGRES_READ_TIME_WITH_TIMEZONE = Yes
    POSTGRES_SCHEMAS_FOR_TABLE_LISTING = edigeo ign_bd_cadastre ign_bd_carto ign_bd_topo mae metier_inao work cvi etalab
    SQL_STATEMENT:
      DROP TABLE IF EXISTS metier_inao.aire_parcellaire;

      CREATE TABLE metier_inao.aire_parcellaire
      (
        id bigserial NOT NULL,
        new_insee character varying(5),
        new_nomcom character varying(100),
        old_insee character varying(5),
        old_nomcom character varying(100),
        type_ig character varying(10),
        id_app integer,
        appellation character varying(150),
        id_denom integer,
        denomination character varying(150),
        crinao character varying(100),
        geom geometry(MultiPolygon,2154),
        CONSTRAINT aire_parcellaire_pkey PRIMARY KEY (id)
      )
      WITH (
        OIDS=FALSE
      );
      ALTER TABLE metier_inao.aire_parcellaire
        OWNER TO postgres;
      GRANT ALL ON TABLE metier_inao.aire_parcellaire TO postgres;
      GRANT ALL ON TABLE metier_inao.aire_parcellaire TO gp_dev;
      GRANT SELECT ON TABLE metier_inao.aire_parcellaire TO gp_inao;

      INSERT INTO metier_inao.aire_parcellaire
      SELECT
      	id_zone id,
      	ch.insee new_insee,
      	ch.nom new_nomcom,
      	tz.insee old_insee,
      	UPPER(UNACCENT(nomcom)) old_nomcom,
      	'AOC' type_ig,
      	ts.id_app,
      	ts.appellation,
      	ts.id_denom,
      	ts.denomination,
      	tc.crinao,
      	tz.geom
      FROM metier_inao.t_siqo ts
      INNER JOIN metier_inao.t_aire ta USING(id_siqo)
      INNER JOIN metier_inao.l_aire_zone USING(id_aire)
      INNER JOIN metier_inao.t_zone tz USING(id_zone)
      LEFT JOIN metier_inao.t_crinao tc USING(id_crinao)
      LEFT JOIN ign_admin_express.commune_histo ch ON ST_INTERSECTS(ST_POINTONSURFACE(tz.geom),ch.geom)
      WHERE type_zone = 2
      AND  ch.date = 2019
      ORDER BY denomination, new_insee

      SELECT
      	 id,
      	 new_insee,
      	 new_nomcom,
      	 old_insee,
      	 old_nomcom,
      	 type_ig,
           id_app,
      	 appellation,
      	 id_denom,
      	 denomination,
      	 crinao
      FROM metier_inao.aire_parcellaire;
    RESULT -> SQLCreator_Result
SQLCreator_Result: Inspector

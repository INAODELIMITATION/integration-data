FME workspace 2_aire_parcellaire_annule_et_remplace.fmw

Note: Nouveaux enregistrements à intégrés work.integration
SQLCreator
    DATASET = srv_sig
    EXPOSED_ATTRIBUTE_LIST = aoc,id_aire,insee,lbl_aire,geometry
    FORMAT = POSTGRES
    POSTGRES_CREATE_FEATURE_TABLES_FROM_DATA = Yes
    POSTGRES_NAMED_CONNECTION = srv_sig
    POSTGRES_QUERY_FEATURE_TYPES_FOR_MERGE_FILTERS = Yes
    POSTGRES_READ_TIME_WITH_TIMEZONE = Yes
    POSTGRES_SCHEMAS_FOR_TABLE_LISTING = edigeo ign_bd_cadastre ign_bd_carto ign_bd_topo mae metier_inao work cvi etalab
    SQL_STATEMENT:
      UPDATE work.live_result lr
      SET lbl_aire = ta.lbl_aire
      FROM metier_inao.t_aire ta
      WHERE lr.id_aire = ta.id_aire;

      SELECT insee, id_aire, lbl_aire, ST_ASTEXT(ST_MULTI(ST_COLLECTIONEXTRACT(ST_UNION(geom),3))) geometry
      FROM work.live_result
      GROUP BY insee, id_aire, lbl_aire;
    RESULT -> FeatureMerger [REQUESTOR]
Note: Enregistrements de la base de données
SQLCreator_2
    DATASET = srv_sig
    EXPOSED_ATTRIBUTE_LIST = id_aire,lbl_aire,insee,nomcom,id_zone
    FORMAT = POSTGRES
    POSTGRES_CREATE_FEATURE_TABLES_FROM_DATA = Yes
    POSTGRES_NAMED_CONNECTION = srv_sig
    POSTGRES_QUERY_FEATURE_TYPES_FOR_MERGE_FILTERS = Yes
    POSTGRES_READ_TIME_WITH_TIMEZONE = Yes
    POSTGRES_SCHEMAS_FOR_TABLE_LISTING = edigeo ign_bd_cadastre ign_bd_carto ign_bd_topo mae metier_inao work cvi etalab
    SQL_STATEMENT:
      SELECT id_aire, lbl_aire, id_zone, insee, nomcom
      FROM metier_inao.t_aire
      INNER JOIN metier_inao.l_aire_zone laz USING(id_aire)
      INNER JOIN metier_inao.t_zone tz USING(id_zone)
      WHERE type_zone = 2
    RESULT -> FeatureMerger [SUPPLIER]
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(insee) @Value(insee) STRING @Value(id_aire) @Value(id_aire) NUM
    MERGE_TYPE = Attributes Only
    PROCESS_DUPS = YES
    REJECT_NULL_MISSING_KEYS = No
    SUPPLIERS_FIRST = No
    MERGED -> SQLExecutor [INITIATOR]
    MERGED -> FeatureMerger_Merged
    UNMERGED_REQUESTOR -> SQLExecutor_2 [INITIATOR]
    UNMERGED_REQUESTOR -> FeatureMerger_UnmergedRequestor
FeatureMerger_Merged: Inspector
Note: SUPPRIME L'ANCIEN ENREGISTREMENT DANS LA TABLE T_ZONE
SQLExecutor [off]
    COMBINE_ATTRS = Keep Initiator Attributes if Conflict
    COMBINE_GEOM = Initiator Geometry Only
    DATASET = srv_sig
    FORMAT = POSTGRES
    POSTGRES_CREATE_FEATURE_TABLES_FROM_DATA = Yes
    POSTGRES_NAMED_CONNECTION = srv_sig
    POSTGRES_QUERY_FEATURE_TYPES_FOR_MERGE_FILTERS = Yes
    POSTGRES_READ_TIME_WITH_TIMEZONE = Yes
    POSTGRES_SCHEMAS_FOR_TABLE_LISTING = edigeo ign_bd_cadastre ign_bd_carto ign_bd_topo mae metier_inao work cvi etalab
    SQL_STATEMENT = DELETE from metier_inao.t_zone WHERE id_zone = '@Value(id_zone)';
    INITIATOR -> SQLExecutor_2 [INITIATOR]
Note: LES NOMS DE COMMUNES SONT CONVERTIS EN UTF8 DANS LA REQUETE SQL AVEC LA FONCTION CONVERT()
Note: CREATION DU NOUVEL ENREGISTREMENT DANS LA TABLE T_ZONE & RECUPERATION DE L'ID
SQLExecutor_2 [off]
    COMBINE_ATTRS = Keep Result Attributes if Conflict
    COMBINE_GEOM = Initiator Geometry Only
    DATASET = srv_sig
    EXPOSED_ATTRIBUTE_LIST = id_zone
    FORMAT = POSTGRES
    POSTGRES_CREATE_FEATURE_TABLES_FROM_DATA = Yes
    POSTGRES_NAMED_CONNECTION = srv_sig
    POSTGRES_QUERY_FEATURE_TYPES_FOR_MERGE_FILTERS = Yes
    POSTGRES_READ_TIME_WITH_TIMEZONE = Yes
    POSTGRES_SCHEMAS_FOR_TABLE_LISTING = edigeo ign_bd_cadastre ign_bd_carto ign_bd_topo mae metier_inao work cvi etalab
    SQL_STATEMENT:
      INSERT INTO metier_inao.t_zone (type_zone, insee, geom)
      VALUES (
          2,
          '@Value(insee)',
          ST_GEOMETRYFROMTEXT('@Value(geometry)',2154)
          ) RETURNING id_zone
    RESULT -> SQLExecutor_3 [INITIATOR]
Note: UN PROBLEME LIE AU CONTRAINTE DE CLE SECONDAIRE EST A REGLE ! / Pour le moment la contraite est inexistante... pour permettre au script de fonctionner correctement / Il faut également prévoir de créer un TRIGGER sur la mise à jour du nom de commune dans T_ZONE & INSEE qui se fait mal
Note: CREATION DE L 'ASSOCIATION AVEC UNE AIRE DANS L_AIRE_ZONE (ID_AIRE,IDZONE)
SQLExecutor_3
    COMBINE_ATTRS = Result Attributes Only
    COMBINE_GEOM = Initiator Geometry Only
    DATASET = srv_sig
    EXPOSED_ATTRIBUTE_LIST = id_zone
    FORMAT = POSTGRES
    POSTGRES_CREATE_FEATURE_TABLES_FROM_DATA = Yes
    POSTGRES_NAMED_CONNECTION = srv_sig
    POSTGRES_QUERY_FEATURE_TYPES_FOR_MERGE_FILTERS = Yes
    POSTGRES_READ_TIME_WITH_TIMEZONE = Yes
    POSTGRES_SCHEMAS_FOR_TABLE_LISTING = edigeo ign_bd_cadastre ign_bd_carto ign_bd_topo mae metier_inao work cvi etalab
    SQL_STATEMENT:
      INSERT INTO metier_inao.l_aire_zone (id_aire, id_zone) VALUES ('@Value(id_aire)','@Value(id_zone)') RETURNING id_zone;

      UPDATE metier_inao.t_zone tz
      SET nomcom = CASE WHEN nomcom is null THEN nom2012 ELSE nomcom END
      FROM insee.historique hist
      WHERE tz.insee = hist.insee2012;
    RESULT -> SQLExecutor_3_Result
SQLExecutor_3_Result: Inspector
FeatureMerger_UnmergedRequestor: Inspector

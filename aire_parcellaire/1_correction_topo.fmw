FME workspace 1_correction_topo.fmw

Parameters:
- SourceDataset_ESRISHAPE = ""\\srv-34db\data2\BDDC\@_martin\1_integration-data\aire_parcellaire\2_vecteur pour integration bdd\non traite\84104_SABLET_Côtes_du_Rhône_DF_1985_06_assemble.shp" "\\srv-34db\data2\BDDC\@_martin\1_integration-data\aire_parcellaire\2_vecteur pour integration bdd\non traite\resultat_bourgogne_blanc_exclusif.shp" "\\srv-34db\data2\BDDC\@_martin\1_integration-data\aire_parcellaire\2_vecteur pour integration bdd\non traite\resultat_bourgogne_toutes_couleurs.shp" "\\srv-34db\data2\BDDC\@_martin\1_integration-data\aire_parcellaire\2_vecteur pour integration bdd\non traite\resultat_macon_rouge_exclusif.shp" "\\srv-34db\data2\BDDC\@_martin\1_integration-data\aire_parcellaire\2_vecteur pour integration bdd\non traite\resultat_macon_toutes_couleurs.shp" "\\srv-34db\data2\BDDC\@_martin\1_integration-data\aire_parcellaire\2_vecteur pour integration bdd\non traite\resultat_macon_village.shp""   # Source Esri Shapefile(s)
- FEATURE_TYPES =

Readers:
- ESRISHAPE_1: ESRISHAPE from $(SourceDataset_ESRISHAPE)

Writers:
- POSTGIS_1: POSTGIS to srv_sig

84104_SABLET_Côtes_du_Rhône_DF_1985_06_assemble (reader ESRISHAPE_1)
    attributes: INSEE char(6), COMMUNE char(30), NOM_AOC char(30), COULEUR_AO char(10), CODE_CVI char(10), REF_APPROB char(30), SURF_DGFiP float, URL_FICHE char(120), commune char(200), aire double, aoc char(200), filename char(200), exclude short, insee char(254), couleur char(200)
    -> AttributeManager
AttributeManager
    ATTR_TABLE:
      RENAME_SET_VALUE INSEE > insee
      REMOVE COMMUNE
      REMOVE NOM_AOC
      REMOVE COULEUR_AO
      REMOVE CODE_CVI
      REMOVE REF_APPROB
      REMOVE SURF_DGFiP
      REMOVE URL_FICHE
      REMOVE commune
      REMOVE aire
      REMOVE aoc
      REMOVE filename
      REMOVE exclude
      REMOVE couleur
      REMOVE fme_feature_type
      RENAME_SET_VALUE fme_dataset > dataset
    -> FeatureWriter [Result]
FeatureWriter
    COORDSYS = EPSG:2154
    DATASET = srv_sig
    DATASET_ATTR = _dataset
    FEATURE_TYPE_LIST_ATTR = _feature_type
    FORMAT = POSTGIS
    POSTGIS_BULK_COPY = YES
    POSTGIS_COORDINATE_SYSTEM_GRANULARITY = FEATURE_TYPE
    POSTGIS_GENERIC_GEOMETRY = no
    POSTGIS_INSERT_TEXT_GEOMETRY = NO
    POSTGIS_LOWERCASE_ATTRIBUTE_NAMES = No
    POSTGIS_NAMED_CONNECTION = srv_sig
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> SQLExecutor [INITIATOR]
SQLExecutor
    COMBINE_ATTRS = Result Attributes Only
    COMBINE_GEOM = Result Geometry Only
    DATASET = srv_sig
    FORMAT = POSTGIS
    POSTGIS_CREATE_FEATURE_TABLES_FROM_DATA = Yes
    POSTGIS_DISABLE_COLLECTION_SPLITTING = yes
    POSTGIS_NAMED_CONNECTION = srv_sig
    POSTGIS_QUERY_FEATURE_TYPES_FOR_MERGE_FILTERS = Yes
    POSTGIS_READ_TIME_WITH_TIMEZONE = Yes
    POSTGIS_SCHEMAS_FOR_TABLE_LISTING = metier_inao work public
    POSTGIS_USE_TRUE_POSTGIS_TYPES = yes
    SQL_STATEMENT:
      DROP TABLE IF EXISTS work.live_result;

      CREATE TABLE work.live_result(
          id serial primary key,
          insee text,
          loc_insee text,
          id_aire integer,
          lbl_aire text,
          dataset text,
          geom geometry(multipolygon,2154));

      CREATE INDEX ON work.live_result USING GIST(geom);

      INSERT INTO work.live_result (insee, dataset, geom)
      SELECT
          insee,
          dataset,
          ST_MULTI(ST_COLLECTIONEXTRACT(ST_MAKEVALID(ST_UNION(geom)),3)) geom
      FROM
      	(SELECT
              insee,
              dataset,
              ST_MAKEVALID(ST_SNAPTOGRID((ST_DUMP(geom)).geom,0.01)) geom
      	FROM work.live) req1
      GROUP BY insee, dataset;

      DROP TABLE IF EXISTS work.live;

      UPDATE work.live_result lr
      SET loc_insee = c.id
      FROM edigeo.commune  c
      WHERE ST_intersects(st_pointonsurface(lr.geom),c.geom);
    INITIATOR -> FeatureReader [INITIATOR]
FeatureReader
    ATTRIBUTES = work.live_result,"id,insee,loc_insee,id_aire,lbl_aire,dataset"
    ATTR_ACCUM_MODE = Only Use Result
    COMBINE_GEOM = Use Result
    COORDSYS = EPSG:2154
    DATASET = srv_sig
    FEATURETYPES = work.live_result
    FORMAT = POSTGIS
    INTERACT = <No Spatial Filter>
    OUTPUT_FEATURES_DISPLAY = Data Features
    POSTGIS_CREATE_FEATURE_TABLES_FROM_DATA = Yes
    POSTGIS_DISABLE_COLLECTION_SPLITTING = yes
    POSTGIS_FEATURES_PER_FETCH = 10000
    POSTGIS_NAMED_CONNECTION = srv_sig
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    work.live_result -> FeatureReader_work.live_result
FeatureReader_work.live_result: Inspector

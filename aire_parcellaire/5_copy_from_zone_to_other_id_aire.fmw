FME workspace 5_copy_from_zone_to_other_id_aire.fmw

Parameters:
- insee_com_a_dupliquer = 34000,34002   # liste des insee des commune à dupliquer
- id_aire_in = 1059   # id_aire à récupérer
- id_aire_out =   # id_aire à générer

Note: lancement du programme
Creator
    GEOMTYPE = Geometry Object
    NUM = 1
    CREATED -> ParameterFetcher
ParameterFetcher
    ATTR_LIST = _insee_com_a_dupliquer $(insee_com_a_dupliquer)
    -> SQLExecutor [INITIATOR]
SQLExecutor
    COMBINE_ATTRS = Result Attributes Only
    COMBINE_GEOM = Initiator Geometry Only
    DATASET = srv_sig_1
    EXPOSED_ATTRIBUTE_LIST = id_aire,lbl_aire,id_zone,insee,nomcom,last_update
    FORMAT = POSTGRES
    POSTGRES_NAMED_CONNECTION = srv_sig_1
    POSTGRES_QUERY_FEATURE_TYPES_FOR_MERGE_FILTERS = Yes
    POSTGRES_READ_TIME_WITH_TIMEZONE = Yes
    POSTGRES_SCHEMAS_FOR_TABLE_LISTING = edigeo ign_bd_cadastre ign_bd_carto ign_bd_topo mae metier_inao work cvi etalab
    SQL_STATEMENT:
      SELECT id_zone, id_aire, lbl_aire, insee, nomcom, t_zone.last_update
      FROM metier_inao.t_aire
      FULL JOIN metier_inao.l_aire_zone USING(id_aire)
      FULL JOIN metier_inao.t_zone USING(id_zone)
      INNER JOIN (SELECT unnest(regexp_split_to_array('$(insee_com_a_dupliquer)',',')) insee)req USING(insee)
      WHERE type_zone = 2
      AND id_aire = $(id_aire_in)
    RESULT -> AttributeSplitter_Output
AttributeSplitter_Output: Inspector

FME workspace 3_maj_excel_bilan_db.fmw

Parameters:
- SourceDataset_XLSXR = \\nas-34d2\Data2\Data2\BDDC\8_vecteur_pour_base\bilan_db.xlsx   # Source Microsoft Excel File(s)
- FEATURE_TYPES = inventaire
- DestDataset_XLSXW = \\nas-34d2\Data2\Data2\BDDC\8_vecteur_pour_base\bilan_db.xlsx   # Destination Microsoft Excel File
- DestDataset_XLSXW_3 = \\nas-34d2\Data2\Data2\BDDC\8_vecteur_pour_base\bilan_db.xlsx   # Destination Microsoft Excel File

Readers:
- XLSXR_1: XLSXR from $(SourceDataset_XLSXR)

Writers:
- XLSXW_1: XLSXW to $(DestDataset_XLSXW)
- XLSXW_2: XLSXW to $(DestDataset_XLSXW_3)

inventaire (reader XLSXR_1)
    attributes: UID number(4,0), siqo_site string, siqo_code_insee char(6), siqo_nom_com char(31), siqo_id_app number(5,0), siqo_appellation char(73), siqo_id_denom number(5,0), siqo_denomination char(73), etat_general char(26), etat_db char(11), inv_cp date, inv_np char(11), inv_agent char(11), commentaire char(144), file_name char(437)
    -> FeatureMerger [REQUESTOR]
SQLCreator
    SQL_STATEMENT:
      SELECT DISTINCT "old_insee", "id_denom","appellation","denomination", "old_nomcom", "id"
      FROM "work"."aire_parcellaire"
      WHERE drop_doublon is null
    EXPOSED_ATTRIBUTE_LIST = id_denom,old_insee,appellation,denomination,old_nomcom,id
    FORMAT = POSTGRES
    DATASET = local
    POSTGRES_QUERY_FEATURE_TYPES_FOR_MERGE_FILTERS = Yes
    POSTGRES_NAMED_CONNECTION = local
    POSTGRES_SCHEMAS_FOR_TABLE_LISTING = work
    RESULT -> FeatureMerger [SUPPLIER]
FeatureMerger
    ATTR_ACCUM_MODE = Merge Supplier
    JOIN_KEYS = @Value(siqo_id_denom) @Value(id_denom) AUTO @Value(siqo_code_insee) @Value(old_insee) AUTO
    PROCESS_DUPS = Yes
    CONNECT_Z_MODE = First Wins
    IGNORE_NULLS = No
    REJECT_NULL_MISSING_KEYS = No
    ATTR_CONFLICT_RES = Use Requestor
    MERGE_TYPE = Attributes Only
    GEOM_TYPE = Build Polygons
    SUPPLIERS_FIRST = No
    MERGED -> StringConcatenator
    UNREFERENCED -> StringConcatenator_2
StringConcatenator
    ACTION = Create New Attribute
    PARM_LINE = @Value(old_insee)_@Value(id_denom)
    VAL_ATTR = etat_db
    -> inventaire (writer XLSXW_1)
inventaire (writer XLSXW_1) [off]
    attributes: UID number(4), siqo_site string(20), siqo_code_insee string(6), siqo_nom_com string(31), siqo_id_app number(5), siqo_appellation string(73), siqo_id_denom number(5), siqo_denomination string(73), etat_general string(26), etat_db string(11), inv_cp date(20), inv_np string(11), inv_agent string(11), commentaire string(144), file_name string(437)
StringConcatenator_2
    ACTION = Create New Attribute
    PARM_LINE = @Value(old_insee)_@Value(id_denom)
    VAL_ATTR = etat_db
    -> AttributeManager
AttributeManager
    ATTR_TABLE:
      RENAME_SET_VALUE id_denom > siqo_id_denom
      RENAME_SET_VALUE old_insee > siqo_code_insee
      RENAME_SET_VALUE appellation > siqo_appellation
      RENAME_SET_VALUE denomination > siqo_denomination
      RENAME_SET_VALUE old_nomcom > siqo_nom_com
      RENAME_SET_VALUE id > UID
      SET_TO commentaire = non présent dans la base siqo
    -> inventaire (writer XLSXW_2)
inventaire (writer XLSXW_2) [off]
    attributes: UID number(6), siqo_site string(12), siqo_code_insee number(6), siqo_nom_com string(28), siqo_id_app number(5), siqo_appellation string(24), siqo_id_denom number(5), siqo_denomination string(35), etat_general string(26), etat_db string(11), inv_cp number(9), inv_np string(11), inv_agent string(11), commentaire string(55), file_name string(344)

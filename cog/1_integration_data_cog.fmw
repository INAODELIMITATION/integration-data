FME workspace 1_integration_data_cog.fmw

Parameters:
- SourceDataset_DBF = \\srv-34db\data2\BDDC\@_martin\1_integration-data\cog\data sources\mvtcommune-01042019.dbf   # Source dBASE (DBF) File(s)
- DestDataset_POSTGRES = srv_sig   # Connection

Readers:
- DBF_1: DBF from $(SourceDataset_DBF)

Writers:
- POSTGRES_1: POSTGRES to $(DestDataset_POSTGRES)

mvtcommune-01042019 (reader DBF_1)
    attributes: MOD char(2), DATE_EFF char(10), TYPECOM_AV char(4), COM_AV char(5), TNCC_AV char(1), NCC_AV char(48), NCCENR_AV char(48), LIBELLE_AV char(48), TYPECOM_AP char(4), COM_AP char(5), TNCC_AP char(1), NCC_AP char(46), NCCENR_AP char(46), LIBELLE_AP char(46)
    -> DateTimeConverter
Note: INTEGRATION DES DONNEES DU COG DE L'INSEE DANS POSTGRES
DateTimeConverter
    DATETIME_ATTR = DATE_EFF
    IN_FORMAT = %Y-%m-%d
    OUT_FORMAT = FME
    REPAIR_INPUT = NO
    -> AttributeManager
AttributeManager
    ATTR_TABLE:
      RENAME_SET_VALUE MOD > mod
      RENAME_SET_VALUE LIBELLE_AV > libelle_av
      RENAME_SET_VALUE LIBELLE_AP > libelle_ap
      RENAME_SET_VALUE COM_AV > com_av
      RENAME_SET_VALUE TYPECOM_AP > typecom_ap
      RENAME_SET_VALUE NCCENR_AV > nccenr_av
      RENAME_SET_VALUE TYPECOM_AV > typecom_av
      RENAME_SET_VALUE TNCC_AP > tncc_ap
      RENAME_SET_VALUE NCC_AP > ncc_ap
      RENAME_SET_VALUE TNCC_AV > tncc_av
      RENAME_SET_VALUE DATE_EFF > date_eff
      RENAME_SET_VALUE COM_AP > com_ap
      RENAME_SET_VALUE NCCENR_AP > nccenr_ap
      RENAME_SET_VALUE NCC_AV > ncc_av
    NUM_PRIOR_FEATURES = 0
    NUM_SUBSEQUENT_FEATURES = 0
    -> mvtcommune (writer POSTGRES_1)
mvtcommune (writer POSTGRES_1)
    attributes: mod varchar(2), date_eff date, typecom_av varchar(4), com_av varchar(5), tncc_av varchar(1), ncc_av varchar(48), nccenr_av varchar(48), libelle_av varchar(48), typecom_ap varchar(4), com_ap varchar(5), tncc_ap varchar(1), ncc_ap varchar(46), nccenr_ap varchar(46), libelle_ap varchar(46)
ok: Inspector

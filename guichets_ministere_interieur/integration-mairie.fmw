FME workspace integration-mairie.fmw

Parameters:
- SourceDataset_PATH = $(FME_MF_DIR)integration\all_20180226\organismes\**\/   # Source Folder and File Pathnames Folder
- FEATURE_TYPES =
- DestDataset_POSTGRES = srv_sig_1   # Connection

Readers:
- PATH_1: PATH from $(SourceDataset_PATH)

Writers:
- POSTGRES_1: POSTGRES to $(DestDataset_POSTGRES)

PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> FilenamePartExtractor
FilenamePartExtractor
    EXTENSION_ATTR = _extension
    ROOTNAME_ATTR = _rootname
    DIRNAME_ATTR = _dirname
    SRC_ATTR = @Value(fme_dataset)
    DIRPATH_ATTR = _dirpath
    FULLNAME_ATTR = _filename
    -> FeatureReader [INITIATOR]
FeatureReader
    ATTR_ACCUM_MODE = Only Use Result
    SELECTED_PORTS = Organisme
    XML_CLIP_TO_ENVELOPE = NO
    ATTRIBUTES = Organisme,"Adresse.Accessibilité,Adresse.Accessibilité.type,Adresse.CodePostal,Adresse.Ligne{},Adresse.Localisation.Latitude,Adresse.Localisation.Longitude,Adresse.Localisation.Précision,Adresse.NomCommune,Adresse.type,CoordonnéesNum.Email,CoordonnéesNum.Télécopie,CoordonnéesNum.Téléphone,CoordonnéesNum.Url,EditeurSource,Nom,Organisme.codeInsee,Organisme.dateMiseAJour,Organisme.id,Organisme.pivotLocal,Ouverture.PlageJ.PlageH{},Ouverture.PlageJ.PlageH{}.début,Ouverture.PlageJ.PlageH{}.fin,Ouverture.PlageJ.début,Ouverture.PlageJ.fin,xml_fragment,xml_id,xml_matched_element,xml_parent_child_pos,xml_parent_id"
    XML_CONTINUE_ON_GEOM_ERROR = no
    XML_FILE_TYPE = Feature Paths
    XML_XFMAP_FEATURE_PATHS_STRUCTURE:
      <structure
      separator="."
      map-empty-elements="yes"
      matched-prefix="attributes"
      matched-attributes="yes"
      cardinality="+{?}"
      except-expression=""
      structure-prefix=""
      child-position-attribute=""
      attribute-identifier=""
      ui-mode="basic"/>
    FORMAT = XML
    COMBINE_GEOM = Use Result
    XML_USE_SEARCH_ENVELOPE = NO
    DATASET = @Value(path_windows)
    INTERACT = <No Spatial Filter>
    XML_XFMAP_FEATURE_PATHS = Organisme
    OUTPUT_FEATURES_DISPLAY = Schema and Data Features
    Organisme -> AttributeManager
AttributeManager
    ATTR_TABLE:
      REMOVE Adresse.Accessibilité
      REMOVE Adresse.Accessibilité.type
      RENAME_SET_VALUE Adresse.CodePostal > CodePostal
      RENAME_SET_VALUE Adresse.Localisation.Latitude > Latitude
      RENAME_SET_VALUE Adresse.Localisation.Longitude > Longitude
      RENAME_SET_VALUE Adresse.Localisation.Précision > Précision
      RENAME_SET_VALUE Adresse.NomCommune > NomCommune
      RENAME_SET_VALUE Adresse.type > type
      RENAME_SET_VALUE CoordonnéesNum.Email > Email
      RENAME_SET_VALUE CoordonnéesNum.Téléphone > telephone
      REMOVE EditeurSource
      RENAME_SET_VALUE Organisme.codeInsee > codeInsee
      RENAME_SET_VALUE Organisme.dateMiseAJour > dateMiseAJour
      RENAME_SET_VALUE Organisme.id > id
      REMOVE Organisme.pivotLocal
      REMOVE xml_fragment
      REMOVE xml_id
      REMOVE xml_matched_element
      REMOVE xml_parent_child_pos
      REMOVE xml_parent_id
      RENAME_SET_VALUE CoordonnéesNum.Télécopie > Telecopie
      RENAME_SET_VALUE CoordonnéesNum.Url > Url
      REMOVE Adresse.Ligne{}
      REMOVE Ouverture.PlageJ.PlageH{}
      REMOVE Ouverture.PlageJ.PlageH{}.début
      REMOVE Ouverture.PlageJ.PlageH{}.fin
      REMOVE Ouverture.PlageJ.début
      REMOVE Ouverture.PlageJ.fin
    -> BulkAttributeRenamer
BulkAttributeRenamer
    ATTRCHOICE = All Attributes
    MODE_CHOICE = RENAME
    CASE_CHANGE_TYPE = lower
    PATTERN_ACTION_DISP = CASECHANGE
    -> etalab.mairie (writer POSTGRES_1)
etalab.mairie (writer POSTGRES_1)
    attributes: codepostal varchar(200), latitude varchar(200), longitude varchar(200), précision varchar(200), nomcommune varchar(200), type varchar(200), email varchar(200), telephone varchar(200), nom varchar(200), codeinsee varchar(200), datemiseajour varchar(200), id varchar(200), telecopie varchar(200), url varchar(200)

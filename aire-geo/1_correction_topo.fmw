FME workspace 1_correction_topo.fmw

Parameters:
- SourceDataset_ESRISHAPE = \\srv-34db\data2\BDDC\@_martin\1_integration-data\aire-geo\1_aire_geo\2019-03-22_aire-geo.shp   # Source Esri Shapefile(s)

Readers:
- ESRISHAPE_1: ESRISHAPE from $(SourceDataset_ESRISHAPE)

Writers:
- POSTGIS_1: POSTGIS to srv_sig_1

2019-03-22_aire-geo (reader ESRISHAPE_1)
    attributes: id number(20,0), signe char(200), id_app long, id_denom long, denominati char(254), url_fiche char(254), url_cdc char(254), CATEGORIE char(50), Classe_UE char(62)
    -> AttributeManager
AttributeManager
    ATTR_TABLE:
      REMOVE id
      REMOVE signe
      RENAME_SET_VALUE denominati > dataset
      REMOVE url_fiche
      REMOVE url_cdc
      REMOVE CATEGORIE
      REMOVE Classe_UE
      SET_TO id_siqo = @PadLeft(@Value(id_app),4,0)@PadLeft(@Value(id_denom),4,0)
    -> AttributeEncoder
AttributeEncoder
    ATTRCHOICE = All Attributes
    DEST_ENCODING = utf-8
    TREAT_AS_BYTES = Honor Encoding
    -> FeatureWriter [Result]
FeatureWriter
    COORDSYS = EPSG:2154
    DATASET = srv_sig_1
    DATASET_ATTR = _dataset
    FEATURE_TYPE_LIST_ATTR = _feature_type
    FORMAT = POSTGIS
    POSTGIS_BULK_COPY = YES
    POSTGIS_COORDINATE_SYSTEM_GRANULARITY = FEATURE_TYPE
    POSTGIS_GENERIC_GEOMETRY = no
    POSTGIS_INSERT_TEXT_GEOMETRY = NO
    POSTGIS_LOWERCASE_ATTRIBUTE_NAMES = No
    POSTGIS_NAMED_CONNECTION = srv_sig_1
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> SQLExecutor [INITIATOR]
SQLExecutor
    COMBINE_ATTRS = Result Attributes Only
    COMBINE_GEOM = Result Geometry Only
    DATASET = srv_sig_1
    FORMAT = POSTGIS
    POSTGIS_DISABLE_COLLECTION_SPLITTING = yes
    POSTGIS_NAMED_CONNECTION = srv_sig_1
    POSTGIS_QUERY_FEATURE_TYPES_FOR_MERGE_FILTERS = Yes
    POSTGIS_READ_TIME_WITH_TIMEZONE = Yes
    POSTGIS_SCHEMAS_FOR_TABLE_LISTING = metier_inao work public
    POSTGIS_USE_TRUE_POSTGIS_TYPES = yes
    SQL_STATEMENT:
      DROP TABLE IF EXISTS work.live_result;

      CREATE TABLE work.live_result(
          id serial primary key,
          id_siqo char(8),
          id_aire integer,
          dataset text,
          geom geometry(multipolygon,2154));

      CREATE INDEX ON work.live_result USING GIST(geom);

      INSERT INTO work.live_result (id_siqo, id_aire, dataset, geom)
      SELECT
          id_siqo,
          ta.id_aire,
          dataset,
          ST_MULTI(ST_COLLECTIONEXTRACT(ST_MAKEVALID(ST_UNION(geom)),3)) geom
      FROM
          (SELECT
              id_siqo,
              dataset,
              ST_MAKEVALID(ST_SNAPTOGRID((ST_DUMP(geom)).geom,0.01)) geom
          FROM work.live)req
      LEFT JOIN metier_inao.t_siqo ts USING(id_siqo)
      LEFT JOIN metier_inao.t_aire ta USING(id_siqo)
      GROUP BY id_siqo, req.denomination, dataset, id_aire;

      DROP TABLE IF EXISTS work.live;
    INITIATOR -> FeatureReader [INITIATOR]
FeatureReader
    ATTRIBUTES = work.live_result,"id,id_siqo,denomination,id_aire,lbl_aire,dataset"
    ATTR_ACCUM_MODE = Only Use Result
    COMBINE_GEOM = Use Result
    COORDSYS = EPSG:2154
    DATASET = srv_sig_1
    FEATURETYPES = work.live_result
    FORMAT = POSTGIS
    INTERACT = <No Spatial Filter>
    OUTPUT_FEATURES_DISPLAY = Data Features
    POSTGIS_DISABLE_COLLECTION_SPLITTING = yes
    POSTGIS_FEATURES_PER_FETCH = 10000
    POSTGIS_NAMED_CONNECTION = srv_sig_1
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    work.live_result -> SQLExecutor_Result
SQLExecutor_Result: Inspector

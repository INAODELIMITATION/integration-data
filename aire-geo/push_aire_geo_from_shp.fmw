FME workspace push_aire_geo_from_shp.fmw

Parameters:
- SourceDataset_ESRISHAPE = $(FME_MF_DIR)1_aire_geo\AOC_AIRE_GEO_FRANCE.shp   # Source Esri Shapefile(s)
- SourceDataset_ESRISHAPE_5 = $(FME_MF_DIR)1_aire_geo\IG_AIRE_GEO_FRANCE.shp   # Source Esri Shapefile(s)
- SourceDataset_ESRISHAPE_4 = $(FME_MF_DIR)1_aire_geo\IGP_AIRE_GEO_FRANCE.shp   # Source Esri Shapefile(s)
- DestDataset_POSTGIS = srv_sig_1   # Connection

Readers:
- ESRISHAPE_1: ESRISHAPE from $(SourceDataset_ESRISHAPE)
- ESRISHAPE_2: ESRISHAPE from $(SourceDataset_ESRISHAPE_5)
- ESRISHAPE_3: ESRISHAPE from $(SourceDataset_ESRISHAPE_4)

Writers:
- POSTGIS_1: POSTGIS to $(DestDataset_POSTGIS)

AOC_AIRE_GEO_FRANCE (reader ESRISHAPE_1)
    attributes: id_app long, id_denom long, denominati char(200), url_fiche char(254), url_cdc char(254)
    -> AttributeCreator_2
AttributeCreator_2
    ATTR_TABLE = SET_TO signe = aoc
    -> AttributeManager
IG_AIRE_GEO_FRANCE (reader ESRISHAPE_2)
    attributes: id_app long, id_denom long, denominati char(150), url_fiche char(254), url_cdc char(254), SURF_HA double
    -> AttributeCreator
AttributeCreator
    ATTR_TABLE = SET_TO signe = ig
    -> AttributeManager
IGP_AIRE_GEO_FRANCE (reader ESRISHAPE_3)
    attributes: id_app long, id_denom long, denominati char(39), url_fiche char(200), url_cdc char(200), Surf_ha double
    -> AttributeCreator_3
AttributeCreator_3
    ATTR_TABLE = SET_TO signe = igp
    -> AttributeManager
AttributeManager
    ATTR_TABLE:
      SET_TO id
      SET_TO denomination
      RENAME_SET_VALUE denominati > denom
      REMOVE SURF_HA
      REMOVE Surf_ha
    -> Counter
Counter
    CNT_ATTR = id
    DOMAIN = counter
    SCOPE = Global
    START = 0
    -> aire_geo (writer POSTGIS_1)
aire_geo (writer POSTGIS_1)
    attributes: id int8,PrimaryKey, signe varchar(200), id_app int4, id_denom int4, id_app int4, id_denom int4, denom varchar(150), denomination varchar(300), url_fiche varchar(254), url_cdc varchar(254)

FME workspace en_cours.fmw

Parameters:
- SourceDataset_ESRISHAPE = $(FME_MF_DIR)geofla\**\*.shp   # Source Esri Shapefile(s)
- FEATURE_TYPES =
- SourceDataset_ESRISHAPE_3 = ""$(FME_MF_DIR)adminexpress\2018_ADMINEXPRESS\ADMIN-EXPRESS_1-1__SHP__FRA_2018-04-17\ADMIN-EXPRESS\1_DONNEES_LIVRAISON_2018-04-17\ADE_1-1_SHP_LAMB93_FR\COMMUNE.shp" "$(FME_MF_DIR)adminexpress\2019_ADMINEXPRESS\ADMIN-EXPRESS_2-0__SHP__FRA_2019-01-18\ADMIN-EXPRESS\1_DONNEES_LIVRAISON_2019-01-18\ADE_2-0_SHP_LAMB93_FR\COMMUNE.shp""   # Source Esri Shapefile(s)
- FEATURE_TYPES_2 =
- DestDataset_POSTGIS = srv_sig   # Connection

Readers:
- ESRISHAPE_1: ESRISHAPE from $(SourceDataset_ESRISHAPE)
- ESRISHAPE_2: ESRISHAPE from $(SourceDataset_ESRISHAPE_3)

Writers:
- POSTGIS_1: POSTGIS to $(DestDataset_POSTGIS)

COMMUNE (reader ESRISHAPE_2)
    attributes: ID char(24), NOM_COM char(50), NOM_COM_M char(50), INSEE_COM char(5), STATUT char(24), POPULATION long, INSEE_ARR char(2), NOM_DEP char(30), INSEE_DEP char(3), NOM_REG char(35), INSEE_REG char(2), CODE_EPCI char(9)
    -> AttributeManager
COMMUNE (reader ESRISHAPE_1)
    attributes: ID_GEOFLA char(255), CODE_COMM char(3), INSEE_COM char(5), NOM_COMM char(50), STATUT char(255), X_CHF_LIEU long, Y_CHF_LIEU long, X_CENTROID long, Y_CENTROID long, Z_MOYEN short, SUPERFICIE char(255), POPULATION char(255), CODE_CANT char(2), CODE_ARR char(1), CODE_DEPT char(2), NOM_DEPT char(30), CODE_REG char(2), NOM_REGION char(30), NOM_COM char(50), NATURE char(255), CODE_COM char(3), NOM_REG char(255)
    -> AttributeManager
AttributeManager
    ATTR_TABLE:
      REMOVE ID_GEOFLA
      REMOVE CODE_COMM
      RENAME_SET_VALUE INSEE_COM > insee
      RENAME_SET_VALUE NOM_COMM > nom
      REMOVE STATUT
      REMOVE X_CHF_LIEU
      REMOVE Y_CHF_LIEU
      REMOVE X_CENTROID
      REMOVE Y_CENTROID
      REMOVE Z_MOYEN
      REMOVE SUPERFICIE
      REMOVE POPULATION
      REMOVE CODE_CANT
      REMOVE CODE_ARR
      RENAME_SET_VALUE CODE_DEPT > dep
      REMOVE NOM_DEPT
      REMOVE CODE_REG
      REMOVE NOM_REGION
      RENAME_SET_VALUE NOM_COM > nom
      REMOVE NATURE
      REMOVE CODE_COM
      REMOVE NOM_REG
      RENAME_SET_VALUE fme_dataset > filename
      REMOVE INSEE_REG
      REMOVE NOM_DEP
      REMOVE ID
      REMOVE CODE_EPCI
      REMOVE INSEE_ARR
      RENAME_SET_VALUE INSEE_DEP > dep
      RENAME_SET_VALUE NOM_COM_M > nom
    -> Tester
Tester
    BOOL_OP = OR
    COMPOSITE_TEST = 1
    TEST_CLAUSE = TEST insee NOT_ATTRIBUTE_VALUE_NULL ""
    TEST_MODE = TEST
    PASSED -> StringSearcher
StringSearcher
    CASE = no
    MATCHED_PARTS_ATTR = list
    MATCHED_RESULT_ATTR = date
    REGEXP = (?:\\)(\d{4})(?:_)
    STRING_TO_SEARCH = @Value(filename)
    MATCHED -> ListIndexer
ListIndexer
    INDEX = 0
    LIST_ATTR = list{}
    -> AttributeManager_2
AttributeManager_2
    ATTR_TABLE:
      REMOVE date
      REMOVE list{}.part
      REMOVE list{}.startIndex
      RENAME_SET_VALUE part > date
      REMOVE startIndex
    -> _commune.__-Merge
    -> commune_histo (writer POSTGIS_1)
_commune.__-Merge: Inspector
commune_histo (writer POSTGIS_1)
    attributes: insee varchar(5), nom text, dep text, filename text, date int4
